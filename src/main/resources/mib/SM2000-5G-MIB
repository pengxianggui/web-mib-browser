--
-- SM2000-5G-MIB.txt
-- MIB generated by MG-SOFT Visual MIB Builder Version 6.0  Build 88
-- Monday, March 30, 2015 at 08:44:57
--

	SM2000-5G-MIB DEFINITIONS ::= BEGIN

		IMPORTS
			enterprises, Integer32, Unsigned32, OBJECT-TYPE, MODULE-IDENTITY,
			NOTIFICATION-TYPE
				FROM SNMPv2-SMI
			DisplayString, RowStatus
				FROM SNMPv2-TC;

zssroot             OBJECT IDENTIFIER ::= { enterprises 43913 }

		-- 1.3.6.1.4.1.43913
		sm2000-5g MODULE-IDENTITY
			LAST-UPDATED "201408180837Z"		-- August 18, 2014 at 08:37 GMT
			ORGANIZATION
				"Zhejiang Science Electronic Technology Co., Ltd"
			CONTACT-INFO
				"
				HuiChuang Building 6/F,
				Jiaxing Advanced Business Park,
				Jiaxing, China.
				"
			DESCRIPTION
				"
				ZSS SM2000-5G Device
				"
			REVISION "201408180837Z"		-- August 18, 2014 at 08:37 GMT
			DESCRIPTION
				" "
			::= { zssroot 16 }



--
-- Type definitions
--

		ActionApply ::= INTEGER
			{
			noapply(0),
			apply(1)
			}

		RebootAction ::= INTEGER
			{
			apply(1)
			}

		TrapVer ::= INTEGER
			{
			v2c(2),
			v3(3)
			}

		V3UserType ::= INTEGER
			{
			snmpnoauth(1),
			snmpmd5(2),
			snmpsha(3),
			snmpmd5des(4),
			snmpmd5aes(5),
			snmpshades(6),
			snmpshaaes(7)
			}

		ActionState ::= INTEGER
			{
			disable(0),
			enable(1)
			}

		RefMode ::= INTEGER
			{
			time(0),
			frequency(1)
			}

		RefCriteria ::= INTEGER
			{
			manual(0),
			priority(1),
			ssm(2)
			}

		SsmOption ::= INTEGER
			{
			option1(1),
			option2(2)
			}

		PktServiceType ::= INTEGER
			{
			ptp-gm(0),
			ntp-sw(2),
			ptp-ntp(4),
			ntp-hw(5)
			}

		CCState ::= INTEGER
			{
			active(0),
			standby(1),
			active-warmup(2),
			standby-warmup(3),
			failed(4),
			disabled(5)
			}

		GPSMode ::= INTEGER
			{
			auto(0),
			manual(1)
			}

		GPSPosMode ::= INTEGER
			{
			survey(0),
			hold(1),
			manual(2)
			}

		GPSHealthy ::= INTEGER
			{
			healthy(1),
			unhealthy(2)
			}

		TrackMode ::= INTEGER
			{
			beidou(0),
			gps(1),
			gps-bd(4),
			glo(5),
			gps-glo(6),
			bd-glo(7),
			gps-bd-glo(8)
			}

		PpsTODPortStatus ::= INTEGER
			{
			disabled(0),
			normal(1),
			error(2)
			}

		PtpTimescale ::= INTEGER
			{
			auto(0),
			arb(1),
			ptp(2)
			}

		PtpProfile ::= INTEGER
			{
			telecom-2008(0),
			default(1),
			hybrid(2),
			itu-g8265-1(3)
			}

		PtpMgmtAddrMode ::= INTEGER
			{
			unicast(0),
			multicast(1)
			}

		PtpActiveProbeFile ::= INTEGER
			{
			telecom-2008(0),
			default(1),
			ethernet-default(2)
			}

		InputFrameType ::= INTEGER
			{
			t2048KHZ(1),
			ccs(2),
			cas(3)
			}

		ClkQL ::= INTEGER
			{
			ql-prc(1),
			ql-unk(2),
			ql-ssut(3),
			ql-ssul(6),
			ql-sec(7),
			ql-dnu(9)
			}

		OutputFrameType ::= INTEGER
			{
			freq2048KHz(1),
			ccs(2),
			cas(3)
			}

		OutputControlE1 ::= INTEGER
			{
			squelch(0),
			on(1),
			ais(2)
			}

		OutputControlFreq ::= INTEGER
			{
			off(0),
			on(1)
			}

		OutputControl ::= INTEGER
			{
			squelch(0),
			on(1)
			}

		OutputCardE1Signal ::= INTEGER
			{
			t2048khz(0),
			cas-ccs(1)
			}

		InputCardFrameType ::= INTEGER
			{
			freq1544KHz(0),
			freq2048KHz(1),
			ccs(2),
			cas(3),
			d4(4),
			esf(5)
			}

		OutputCardFrameType ::= INTEGER
			{
			freq1544KHz(0),
			freq2048KHz(1),
			ccs(2),
			cas(3),
			d4(4),
			esf(5),
			t1mhz(6),
			t5mhz(7),
			t10mhz(8)
			}

		NtpProbeDataFormat ::= INTEGER
			{
			rawstats(0),
			compact(1)
			}

		IpMCMode ::= INTEGER
			{
			static(0),
			dhcp(1)
			}

		FirewallType ::= INTEGER
			{
			telnet(0),
			ssh(1),
			ftp(2),
			sftp(3),
			snmp(4),
			icmp(5)
			}

		FirewallState ::= INTEGER
			{
			block(0),
			allow(1)
			}

		IpPortState ::= INTEGER
			{
			disable(0),
			enable(1),
			restart(2)
			}

		CurrentEthLinkSpeed ::= INTEGER
			{
			none(0),
			t100M(1),
			t1000M(2),
			t10000M(3)
			}

		EthLinkSpeedCfg ::= INTEGER
			{
			t10M(0),
			t100M(1),
			t1000M(2),
			t10000M(3)
			}

		EthLinkSpeedCfg10GE ::= INTEGER
			{
			t1000M(2),
			t10000M(3)
			}

		CCethLinkSpeedCfg ::= INTEGER
			{
			all(0),
			t100M(1),
			t1000M(2),
			t10000M(3)
			}

		AlarmLevel ::= INTEGER
			{
			critical(2),
			major(3),
			minor(4),
			event(5)
			}

		AlarmStatus ::= INTEGER
			{
			cleared(0),
			active(1)
			}

		OutputCfgTestMode ::= INTEGER
			{
			disable(0),
			t1pulse(1)
			}

		UpgradeStatus ::= INTEGER
			{
			no-upgrade(0),
			retrieving-file(1),
			retrieving-file-failed(2),
			updating-flash(3),
			updating-pkg-error(4),
			updating-flash-failed(5),
			upgrade-complete(6)
			}

		RedundancyPortState ::= INTEGER
			{
			inactive(0),
			active(1)
			}

		RedundancyPort ::= INTEGER
			{
			port-a(0),
			port-b(1),
			none(255)
			}

	    OutputPTPOutQLmode ::= INTEGER
	    	{
	    		unidirectional(0),
	    		bidirectional(1)
	    	}

	     OutputPTPtimescale ::= INTEGER
	     	{
	     		auto(0),
	     		arb(1),
	     		ptp(2)
	     	}

	     OutputPTPprofile ::= INTEGER
	     	{
	     		telecom-2008(0),
				default(1),
				itu-g8265-1(3),
	     		ethernet-default(4),
				itu-g8275-1(6),
				itu-g8275-2(7),
				cu-spec(8),
                cm-5G-spec(9)
	     	}

		OutputPTPprofile10GE ::= INTEGER
	     	{
				telecom-2008(0),
				default(1),
				itu-g8265-1(3),
	     		ethernet-default(4),
				itu-g8275-1(6),
				itu-g8275-2(7),
				cu-spec(8),
                cm-5G-spec(9)
	     	}

	    OutputPTPclockstateType ::= INTEGER
	    	{
	    		 unknown(0),
	    		 warmup(1),
	    		 freerun(2),
	    		 fast-track(3),
	    		 normal-track(4),
	    		 holdover(5),
	    		 bridge(6),
	    		 fail(7),
	    		 offline(8),
	    		 extend-holdover(9)
	    	}

	     OutSSMbitType ::= INTEGER
	     	{
	     		ssm-bit4(4),
	     		ssm-bit5(5),
	     		ssm-bit6(6),
	     		ssm-bit7(7),
	     		ssm-bit8(8),
			ssm-bit-all(15)
	     	}

	    EthlinkDuplexType ::= INTEGER
	     	{
	     		full(0),
	     		half(1)
	     	}

	    NtpListState ::= INTEGER
	    	{
	    		none(0),
	    		whitelist(1),
	    		blacklist(2)
	    	}

	    ActionResult ::= INTEGER
	    	{
	    		success(1),
	    		fail(2)
	    	}

	   	OutputFREQtype ::= INTEGER
	   		{
	   			freq-1Hz(0),
	   			freq-2Hz(1),
	   			freq-4Hz(2),
	   			freq-5Hz(3),
	   			freq-10Hz(4),
	   			freq-20Hz(5),
	   			freq-40Hz(6),
	   			freq-50Hz(7),
	   			freq-100Hz(8),
	   			freq-200Hz(9),
	   			freq-400Hz(10),
	   			freq-500Hz(11),
	   			freq-800Hz(12),
	   			freq-1KHz(13),
	   			freq-2KHz(14),
	   			freq-4KHz(15),
	   			freq-5KHz(16),
	   			freq-8KHz(17),
	   			freq-10KHz(18),
	   			freq-20KHz(19),
	   			freq-40KHz(20),
	   			freq-50KHz(21),
	   			freq-100KHz(22),
	   			freq-200KHz(23),
	   			freq-400KHz(24),
	   			freq-500KHz(25),
	   			freq-1MHz(26),
	   			freq-2MHz(27),
	   			freq-4MHz(28),
	   			freq-5MHz(29),
	   			freq-10MHz(30),
	   			freq-20MHz(31)
	   		}

		Inputchn ::= INTEGER
			{
	   			slot1-1(1),
	   			slot1-2(2),
	   			slot1-3(3),
	   			slot1-4(4),
	   			gnss-1(5),
	   			pps-tod-1(6),
	   			irig-1(7),
				pps-1(8),
				freq-10M-1(9),
				sys-1(10),
	   			slot2-1(11),
	   			slot2-2(12),
	   			slot2-3(13),
	   			slot2-4(14),
	   			gnss-2(15),
	   			pps-tod-2(16),
	   			irig-2(17),
				pps-2(18),
				freq-10M-2(19),
				sys-2(20),
				ptp-1(21),
				ptp-2(22),
				ntp-1(23),
				ntp-2(24)
			}

		PPSchn ::= INTEGER
			{
	   			gnss(0),
	   			pps-tod(1),
	   			irig(2),
				pps(3),
				sys(4)
			}

		RedundMode ::= INTEGER
			{
				act-act(0),
	   			act-stdby(1),
				none(2)
			}

		RefManSrc ::= INTEGER
			{

	   			ref-GNSS-1(0),
				ref-GNSS-2(1),
	   			ref-PPS-TOD-1(2),
				ref-PPS-TOD-2(3),
	   			ref-IRIG-1(4),
				ref-IRIG-2(5),
				ref-Slot1-1(6),
	   			ref-Slot1-2(7),
	   			ref-Slot1-3(8),
	   			ref-Slot1-4(9),
	   			ref-Slot2-1(10),
	   			ref-Slot2-2(11),
	   			ref-Slot2-3(12),
	   			ref-Slot2-4(13),
	   			ref-10M-1(14),
				ref-10M-2(15),
				ref-PPS-1(16),
				ref-PPS-2(17),
				ref-PTP-1(18),
				ref-PTP-2(19),
				ref-SYNCE-1(20),
				ref-SYNCE-2(21),
				sys(22),
				ref-NTP-1(23),
				ref-NTP-2(24)
			}

		RefManFreqSrc ::= INTEGER
			{
				ref-Slot1-1(6),
	   			ref-Slot1-2(7),
	   			ref-Slot1-3(8),
	   			ref-Slot1-4(9),
	   			ref-Slot2-1(10),
	   			ref-Slot2-2(11),
	   			ref-Slot2-3(12),
	   			ref-Slot2-4(13),
				ref-10M-1(14),
				ref-10M-2(15),
				none(22)
			}

		MasterOnlyEnable ::= INTEGER
			{
			no(0),
			yes(1)
			}

		InputPTPprofile ::= INTEGER
	     	{
	     		default(0),
	     		telecom2008(1),
	     		ethernet-default(2),
	     		itu-g8275-1(3),
			cm-5g-spec(4),
			itu-g8275-2(5)
	     	}

		TtlType ::= INTEGER
			{
				t10M(0),
	   			pps(1)
			}

		SVTYPE ::= INTEGER
			{
			gps(1),
			bd(2)
			}

		EthSrcType ::= INTEGER
			{
				ptp(0),
	   			synce(1),
				ptp-synce(2)
			}

		AclRuleType ::= INTEGER
			{
			deny(0),
			permit(1)
			}

		AclEtherType ::= INTEGER
			{
			arp(0),
			ipv4(1),
			ipv6(2)
			}

		AclSetType ::= INTEGER
			{
			todo(0),
			add(1),
			delete(2)
			}

		CVStationType ::= INTEGER
			{
			server(0),
			client(1),
                        relay(2)
			}


		CVProfileType ::= INTEGER
			{
			cmcc(0),
			sgcc(1)
			}

        CVProfileTypeClient ::= INTEGER
            {
            cmcc(0),
            sgcc(1),
            ntsc(2)
            }

		OutputPTPntpType::= INTEGER
			{
			ntp-software(0),
			ntp-hardware(1)
			}

		OutputPTPntpIpvx ::= INTEGER
			{
			ntp-ipv4(0),
			ntp-ipv6(1)
			}

		EthPortIpType ::= INTEGER
			{
			ipv4(0),
			ipv6(1)
			}

		AclCommit ::= INTEGER
			{
			todo(0),
			commit(1)
			}

--
-- Node definitions
--

		-- 1.3.6.1.4.1.43913.16.1
		inventory OBJECT IDENTIFIER ::= { sm2000-5g 1 }


		-- 1.3.6.1.4.1.43913.16.1.1
		assetNum OBJECT-TYPE
			SYNTAX DisplayString
			MAX-ACCESS read-write
			STATUS current
			DESCRIPTION
				"Inventory asset value is assigned by the user."
			::= { inventory 1 }


		-- 1.3.6.1.4.1.43913.16.1.2
		systemModel OBJECT-TYPE
			SYNTAX DisplayString
			MAX-ACCESS read-only
			STATUS current
			DESCRIPTION
				"The device model value is read-only."
			::= { inventory 2 }


		-- 1.3.6.1.4.1.43913.16.1.3
		inventoryInfoTable OBJECT-TYPE
			SYNTAX SEQUENCE OF InventoryInfoEntry
			MAX-ACCESS not-accessible
			STATUS current
			DESCRIPTION
				"A list of inventory of each MC, CC1, CC2, INPUT1 and INPUT2."
			::= { inventory 3 }


		-- 1.3.6.1.4.1.43913.16.1.3.1
		inventoryInfoEntry OBJECT-TYPE
			SYNTAX InventoryInfoEntry
			MAX-ACCESS not-accessible
			STATUS current
			DESCRIPTION
				"An inventory entry containing objects of each
				module inventory management information."
			INDEX { invIndex }
			::= { inventoryInfoTable 1 }


		InventoryInfoEntry ::=
			SEQUENCE {
				invIndex
					Integer32,
				invModuleID
					DisplayString,
				invSlot
					DisplayString,
				invPartNum
					DisplayString,
				invClEINum
					DisplayString,
				invSerial
					DisplayString,
				invHWVersion
					DisplayString,
				invFPGAVersion
					DisplayString,
				invSWVersion
					DisplayString
			 }

		-- 1.3.6.1.4.1.43913.16.1.3.1.1
		invIndex OBJECT-TYPE
			SYNTAX Integer32 (1..5)
			MAX-ACCESS not-accessible
			STATUS current
			DESCRIPTION
				"The inventory index."
			::= { inventoryInfoEntry 1 }


		-- 1.3.6.1.4.1.43913.16.1.3.1.2
		invModuleID OBJECT-TYPE
			SYNTAX DisplayString
			MAX-ACCESS read-only
			STATUS current
			DESCRIPTION
				"The module ID should be one of  MC, CC1, CC2, INPUT1 or INPUT2."
			::= { inventoryInfoEntry 2 }


		-- 1.3.6.1.4.1.43913.16.1.3.1.3
		invSlot OBJECT-TYPE
			SYNTAX DisplayString
			MAX-ACCESS read-only
			STATUS current
			DESCRIPTION
				"The slot should be the position or location of a module in a chassis."
			::= { inventoryInfoEntry 3 }


		-- 1.3.6.1.4.1.43913.16.1.3.1.4
		invPartNum OBJECT-TYPE
			SYNTAX DisplayString
			MAX-ACCESS read-only
			STATUS current
			DESCRIPTION
				"The current part number is given."
			::= { inventoryInfoEntry 4 }


		-- 1.3.6.1.4.1.43913.16.1.3.1.5
		invClEINum OBJECT-TYPE
			SYNTAX DisplayString
			MAX-ACCESS read-only
			STATUS current
			DESCRIPTION
				"The current CLEI number is given, if assigned."
			::= { inventoryInfoEntry 5 }


		-- 1.3.6.1.4.1.43913.16.1.3.1.6
		invSerial OBJECT-TYPE
			SYNTAX DisplayString
			MAX-ACCESS read-only
			STATUS current
			DESCRIPTION
				"The current serial number is given."
			::= { inventoryInfoEntry 6 }


		-- 1.3.6.1.4.1.43913.16.1.3.1.7
		invHWVersion OBJECT-TYPE
			SYNTAX DisplayString
			MAX-ACCESS read-only
			STATUS current
			DESCRIPTION
				"The current hardware version is given."
			::= { inventoryInfoEntry 7 }


		-- 1.3.6.1.4.1.43913.16.1.3.1.8
		invFPGAVersion OBJECT-TYPE
			SYNTAX DisplayString
			MAX-ACCESS read-only
			STATUS current
			DESCRIPTION
				"The current FPGA version is given."
			::= { inventoryInfoEntry 8 }


		-- 1.3.6.1.4.1.43913.16.1.3.1.9
		invSWVersion OBJECT-TYPE
			SYNTAX DisplayString
			MAX-ACCESS read-only
			STATUS current
			DESCRIPTION
				"The current firmware version is given."
			::= { inventoryInfoEntry 9 }


		-- 1.3.6.1.4.1.43913.16.2
		administration OBJECT IDENTIFIER ::= { sm2000-5g 2 }


		-- 1.3.6.1.4.1.43913.16.2.4
		boardConfig OBJECT IDENTIFIER ::= { administration 4 }


		-- 1.3.6.1.4.1.43913.16.2.4.1
		backupConfigLocal OBJECT-TYPE
			SYNTAX ActionApply
			MAX-ACCESS read-write
			STATUS current
			DESCRIPTION
				"Backup the configurations of imc, ioc1 and ioc2 board to local file system.
				Please select apply(1) or nonapply(0). This field is write-only."
			::= { boardConfig 1 }


		-- 1.3.6.1.4.1.43913.16.2.4.2
		backupConfigCCtoMC OBJECT-TYPE
			SYNTAX ActionApply
			MAX-ACCESS read-write
			STATUS current
			DESCRIPTION
				"Backup a configuration of ioc to imc board. Please select apply(1) or nonapply(0). This field is write-only."
			::= { boardConfig 2 }


		-- 1.3.6.1.4.1.43913.16.2.4.3
		backupConfigMCtoCC OBJECT-TYPE
			SYNTAX ActionApply
			MAX-ACCESS read-write
			STATUS current
			DESCRIPTION
				"Backup a configuration of imc to ioc board. Please select apply(1) or nonapply(0). This field is write-only."
			::= { boardConfig 3 }


		-- 1.3.6.1.4.1.43913.16.2.4.4
		backupConfigCCtoRemote OBJECT-TYPE
			SYNTAX DisplayString
			MAX-ACCESS read-write
			STATUS current
			DESCRIPTION
				"Backup a configuration of ioc to remote. This field is write-only. The command format is:
				file_name,[ftp:]server_ip,user,passwd"
			::= { boardConfig 4 }


		-- 1.3.6.1.4.1.43913.16.2.4.5
		backupConfigMCtoRemote OBJECT-TYPE
			SYNTAX DisplayString
			MAX-ACCESS read-write
			STATUS current
			DESCRIPTION
				"Backup a configuration of imc to remote. This field is write-only. The command format is:
				file_name,[ftp:]server_ip,user,passwd"
			::= { boardConfig 5 }


		-- 1.3.6.1.4.1.43913.16.2.4.6
		restoreFactoryConfig OBJECT-TYPE
			SYNTAX ActionApply
			MAX-ACCESS read-write
			STATUS current
			DESCRIPTION
				"Restore a factory configuration to system. All configuration parameters are reset.
				Please select apply(1) or nonapply(0). This field is write-only."
			::= { boardConfig 6 }


		-- 1.3.6.1.4.1.43913.16.2.4.7
		restoreDefaultConfig OBJECT-TYPE
			SYNTAX ActionApply
			MAX-ACCESS read-write
			STATUS current
			DESCRIPTION
				"Restore a default configuration to system. User logins and IP port configurations are not affected.
				Please select apply(1) or nonapply(0). This field is write-only."
			::= { boardConfig 7 }


		-- 1.3.6.1.4.1.43913.16.2.4.8
		restoreConfigCCtoMC OBJECT-TYPE
			SYNTAX ActionApply
			MAX-ACCESS read-write
			STATUS current
			DESCRIPTION
				"Restore configuration from ioc to imc board. Please select apply(1) or nonapply(0). This field is write-only."
			::= { boardConfig 8 }


		-- 1.3.6.1.4.1.43913.16.2.4.9
		restoreConfigMCtoCC OBJECT-TYPE
			SYNTAX ActionApply
			MAX-ACCESS read-write
			STATUS current
			DESCRIPTION
				"Restore configuration from imc to ioc. Please select apply(1) or nonapply(0). This field is write-only."
			::= { boardConfig 9 }


		-- 1.3.6.1.4.1.43913.16.2.4.10
		restoreConfigRemoteToMC OBJECT-TYPE
			SYNTAX DisplayString
			MAX-ACCESS read-write
			STATUS current
			DESCRIPTION
				"Restore configuration from remote to imc. This field is write-only.The command format is:
				file_name,[ftp:]server_ip,user,passwd"
			::= { boardConfig 10 }


		-- 1.3.6.1.4.1.43913.16.2.4.11
		restoreConfigRemoteToCC OBJECT-TYPE
			SYNTAX DisplayString
			MAX-ACCESS read-write
			STATUS current
			DESCRIPTION
				"Restore configuration from remote to ioc. This field is write-only.The command format is:
				file_name,[ftp:]server_ip,user,passwd"
			::= { boardConfig 11 }


		-- 1.3.6.1.4.1.43913.16.2.5
		reboot OBJECT IDENTIFIER ::= { administration 5 }


		-- 1.3.6.1.4.1.43913.16.2.5.1
		systemReboot OBJECT-TYPE
			SYNTAX RebootAction
			MAX-ACCESS read-write
			STATUS current
			DESCRIPTION
				"Reboot whole system. This item is write-only. The read of this item is invalid.
				Only apply(1) can be set."
			::= { reboot 1 }


		-- 1.3.6.1.4.1.43913.16.2.5.2
		mcReboot OBJECT-TYPE
			SYNTAX RebootAction
			MAX-ACCESS read-write
			STATUS current
			DESCRIPTION
				"Reboot MC board. This value is write-only. The read value is invalid.
				Only apply(1) can be set."
			::= { reboot 2 }


		-- 1.3.6.1.4.1.43913.16.2.5.3
		cc1Reboot OBJECT-TYPE
			SYNTAX RebootAction
			MAX-ACCESS read-write
			STATUS current
			DESCRIPTION
				"Reboot CC1 board. This item is write-only. The read of item is invalid.
				Only apply(1) can be set."
			::= { reboot 3 }


		-- 1.3.6.1.4.1.43913.16.2.5.4
		cc2Reboot OBJECT-TYPE
			SYNTAX RebootAction
			MAX-ACCESS read-write
			STATUS current
			DESCRIPTION
				"Reboot CC2 board. This item is write-only. The read of item is invalid.
				Only apply(1) can be set."
			::= { reboot 4 }


		-- 1.3.6.1.4.1.43913.16.2.5.5
		input1Reboot OBJECT-TYPE
			SYNTAX RebootAction
			MAX-ACCESS read-write
			STATUS current
			DESCRIPTION
				"Reboot input1 board. This item is write-only. The read of item is invalid.
				Only apply(1) can be set."
			::= { reboot 5 }


		-- 1.3.6.1.4.1.43913.16.2.5.6
		input2Reboot OBJECT-TYPE
			SYNTAX RebootAction
			MAX-ACCESS read-write
			STATUS current
			DESCRIPTION
				"Reboot input2 board. This item is write-only. The read of item is invalid.
				Only apply(1) can be set."
			::= { reboot 6 }


		-- 1.3.6.1.4.1.43913.16.2.6
		image OBJECT IDENTIFIER ::= { administration 6 }


		-- 1.3.6.1.4.1.43913.16.2.6.1
		mcImageActive OBJECT-TYPE
			SYNTAX Integer32
			MAX-ACCESS read-write
			STATUS current
			DESCRIPTION
				"MC image active control. This controls which image will be used to boot from.
				The valid setting should be either 1 or 2."
			::= { image 1 }


		-- 1.3.6.1.4.1.43913.16.2.6.2
		cc1ImageActive OBJECT-TYPE
			SYNTAX Integer32
			MAX-ACCESS read-write
			STATUS current
			DESCRIPTION
				"MC image active control. This controls which image will be used to boot from.
				The valid setting should be either 1 or 2."
			::= { image 2 }


		-- 1.3.6.1.4.1.43913.16.2.6.3
		cc2ImageActive OBJECT-TYPE
			SYNTAX Integer32
			MAX-ACCESS read-write
			STATUS current
			DESCRIPTION
				"MC image active control. This controls which image will be used to boot from.
				The valid setting should be either 1 or 2."
			::= { image 3 }


		-- 1.3.6.1.4.1.43913.16.2.6.4
		input1ImageActive OBJECT-TYPE
			SYNTAX Integer32
			MAX-ACCESS read-write
			STATUS current
			DESCRIPTION
				"Input1 card image active control. This controls which image will be used to boot from.
				The valid setting should be either 1 or 2."
			::= { image 4 }


		-- 1.3.6.1.4.1.43913.16.2.6.5
		input2ImageActive OBJECT-TYPE
			SYNTAX Integer32
			MAX-ACCESS read-write
			STATUS current
			DESCRIPTION
				"Input2 card image active control. This controls which image will be used to boot from.
				The valid setting should be either 1 or 2."
			::= { image 5 }


		-- 1.3.6.1.4.1.43913.16.2.6.6
		imageInfoTable OBJECT-TYPE
			SYNTAX SEQUENCE OF ImageInfoEntry
			MAX-ACCESS not-accessible
			STATUS current
			DESCRIPTION
				"A list of image information of each MC, CC1, CC2, INPUT1 and INPUT2."
			::= { image 6 }


		-- 1.3.6.1.4.1.43913.16.2.6.6.1
		imageInfoEntry OBJECT-TYPE
			SYNTAX ImageInfoEntry
			MAX-ACCESS not-accessible
			STATUS current
			DESCRIPTION
				"An entry containing objects of each module's image information."
			INDEX { imageInfoIndex }
			::= { imageInfoTable 1 }


		ImageInfoEntry ::=
			SEQUENCE {
				imageInfoIndex
					Integer32,
				imageInfoModuleID
					DisplayString,
				imageID
					DisplayString,
				imageCurrentState
					DisplayString,
				imageVersion
					DisplayString
			 }

		-- 1.3.6.1.4.1.43913.16.2.6.6.1.1
		imageInfoIndex OBJECT-TYPE
			SYNTAX Integer32 (1..10)
			MAX-ACCESS not-accessible
			STATUS current
			DESCRIPTION
				"The index to represent the number of image info ID."
			::= { imageInfoEntry 1 }


		-- 1.3.6.1.4.1.43913.16.2.6.6.1.2
		imageInfoModuleID OBJECT-TYPE
			SYNTAX DisplayString
			MAX-ACCESS read-only
			STATUS current
			DESCRIPTION
				"The module ID should be one of  MC, CC1, CC2, INPUT1 or INPUT2."
			::= { imageInfoEntry 2 }


		-- 1.3.6.1.4.1.43913.16.2.6.6.1.3
		imageID OBJECT-TYPE
			SYNTAX DisplayString
			MAX-ACCESS read-only
			STATUS current
			DESCRIPTION
				"The image ID range should be 1 to 2."
			::= { imageInfoEntry 3 }


		-- 1.3.6.1.4.1.43913.16.2.6.6.1.4
		imageCurrentState OBJECT-TYPE
			SYNTAX DisplayString
			MAX-ACCESS read-only
			STATUS current
			DESCRIPTION
				"The image current state should be active or backup."
			::= { imageInfoEntry 4 }


		-- 1.3.6.1.4.1.43913.16.2.6.6.1.5
		imageVersion OBJECT-TYPE
			SYNTAX DisplayString
			MAX-ACCESS read-only
			STATUS current
			DESCRIPTION
				"The image version will show the detailed current image message."
			::= { imageInfoEntry 5 }


		-- 1.3.6.1.4.1.43913.16.2.12
		snmp OBJECT IDENTIFIER ::= { administration 12 }


		-- 1.3.6.1.4.1.43913.16.2.12.1
		trapVersion OBJECT-TYPE
			SYNTAX TrapVer
			MAX-ACCESS read-write
			STATUS current
			DESCRIPTION
				"Setup the trap version to SNMP agent. The valid setting should be v2c(2) and v3(3)."
			::= { snmp 1 }


		-- 1.3.6.1.4.1.43913.16.2.12.2
		snmpUserTable OBJECT-TYPE
			SYNTAX SEQUENCE OF SnmpUserEntry
			MAX-ACCESS not-accessible
			STATUS current
			DESCRIPTION
				"This table is used to display the valid SNMP V3 user info.  All SNMP V3 users except trap users should be defined
				in this table. This table's row only can be added or deleted. The existing row can not be modified."
			::= { snmp 2 }


		-- 1.3.6.1.4.1.43913.16.2.12.2.1
		snmpUserEntry OBJECT-TYPE
			SYNTAX SnmpUserEntry
			MAX-ACCESS not-accessible
			STATUS current
			DESCRIPTION
				"This is an entry in the SNMP V3 user table.
				It contains username, user type, and keys."
			INDEX { snmpUserIndex }
			::= { snmpUserTable 1 }


		SnmpUserEntry ::=
			SEQUENCE {
				snmpUserIndex
					Integer32,
				snmpUserName
					DisplayString,
				snmpUserType
					V3UserType,
				snmpUserAuthKey
					DisplayString,
				snmpUserPrivateKey
					DisplayString,
				snmpUserRowStatus
					RowStatus
			 }

		-- 1.3.6.1.4.1.43913.16.2.12.2.1.1
		snmpUserIndex OBJECT-TYPE
			SYNTAX Integer32 (1..10)
			MAX-ACCESS not-accessible
			STATUS current
			DESCRIPTION
				"A unique value for each user entry. This value ranges should be from 1 to 10."
			::= { snmpUserEntry 1 }


		-- 1.3.6.1.4.1.43913.16.2.12.2.1.2
		snmpUserName OBJECT-TYPE
			SYNTAX DisplayString
			MAX-ACCESS read-write
			STATUS current
			DESCRIPTION
				"SNMP V3 user name.  The max length of SNMP V3 user name is 20 characters.
				Only alphanumeric characters and chars {- , _} are acceptable.  Leading characters can't be (- or _)."
			::= { snmpUserEntry 2 }


		-- 1.3.6.1.4.1.43913.16.2.12.2.1.3
		snmpUserType OBJECT-TYPE
			SYNTAX V3UserType
			MAX-ACCESS read-write
			STATUS current
			DESCRIPTION
				"SNMP V3 User type is defined as the follow types:
				1--	snmpNoauth,
				2--	snmpmd5,
				3--	snmpsha,
				4--	snmpmd5des,
				5--	snmpmd5aes,
				6--	snmpshades,
				7--	snmpshaaes.
				"
			::= { snmpUserEntry 3 }


		-- 1.3.6.1.4.1.43913.16.2.12.2.1.4
		snmpUserAuthKey OBJECT-TYPE
			SYNTAX DisplayString
			MAX-ACCESS read-write
			STATUS current
			DESCRIPTION
				"SNMP V3 user authentication key. Only chars {a-z,A-Z,0-9, ! ( ) - _ . ? ~ * @ ^ + = : / %} are acceptable.
				Minimum key length is 8 chars."
			::= { snmpUserEntry 4 }


		-- 1.3.6.1.4.1.43913.16.2.12.2.1.5
		snmpUserPrivateKey OBJECT-TYPE
			SYNTAX DisplayString
			MAX-ACCESS read-write
			STATUS current
			DESCRIPTION
				"Private key of SNMP V3 user. Only chars {a-z,A-Z,0-9, ! ( ) - _ . ? ~ * @ ^ + = : / %} are acceptable.
				Minimum key length is 8 chars."
			::= { snmpUserEntry 5 }


		-- 1.3.6.1.4.1.43913.16.2.12.2.1.6
		snmpUserRowStatus OBJECT-TYPE
			SYNTAX RowStatus
			MAX-ACCESS read-write
			STATUS current
			DESCRIPTION
				"The row status of SNMP user table to control row actions. It has the following actions:

				The status column has six defined values:

				     - `active(1)', which indicates that the conceptual row is
				     available for use by the managed device;

				     - `notInService(2)', which indicates that the conceptual
				     row exists in the agent, but is unavailable for use by
				     the managed device (see NOTE below);

				     - `notReady(3)', which indicates that the conceptual row
				     exists in the agent, but is missing information
				     necessary in order to be available for use by the
				     managed device;

				     - `createAndGo(4)', which is supplied by a management
				     station wishing to create a new instance of a
				     conceptual row and to have its status automatically set
				     to active, making it available for use by the managed
				     device;

				     - `createAndWait(5)', which is supplied by a management
				     station wishing to create a new instance of a
				     conceptual row (but not make it available for use by
				     the managed device); and,

				     - `destroy(6)', which is supplied by a management station
				     wishing to delete all of the instances associated with
				     an existing conceptual row.
				"
			::= { snmpUserEntry 6 }


		-- 1.3.6.1.4.1.43913.16.2.12.3
		snmpManagerTable OBJECT-TYPE
			SYNTAX SEQUENCE OF SnmpManagerEntry
			MAX-ACCESS not-accessible
			STATUS current
			DESCRIPTION
				"This table is used to display SNMP manager info, such as managerID, EngineID, manager IP addresses, etc.
				This table's row only can be added or deleted. The existing row can not be modified."
			::= { snmp 3 }


		-- 1.3.6.1.4.1.43913.16.2.12.3.1
		snmpManagerEntry OBJECT-TYPE
			SYNTAX SnmpManagerEntry
			MAX-ACCESS not-accessible
			STATUS current
			DESCRIPTION
				"This is an entry in the Manager table."
			INDEX { snmpManagerIndex }
			::= { snmpManagerTable 1 }


		SnmpManagerEntry ::=
			SEQUENCE {
				snmpManagerIndex
					Integer32,
				snmpManagerID
					DisplayString,
				snmpManagerAddress
					DisplayString,
				snmpManagerEngineID
					DisplayString,
				snmpManagerRowStatus
					RowStatus
			 }

		-- 1.3.6.1.4.1.43913.16.2.12.3.1.1
		snmpManagerIndex OBJECT-TYPE
			SYNTAX Integer32 (1..5)
			MAX-ACCESS not-accessible
			STATUS current
			DESCRIPTION
				"A unique value for each user entry. This value ranges should be from 1 to 5."
			::= { snmpManagerEntry 1 }


		-- 1.3.6.1.4.1.43913.16.2.12.3.1.2
		snmpManagerID OBJECT-TYPE
			SYNTAX DisplayString
			MAX-ACCESS read-only
			STATUS current
			DESCRIPTION
				"SNMP manager ID or name which is used for SNMP v2 or v3 trap or notification."
			::= { snmpManagerEntry 2 }


		-- 1.3.6.1.4.1.43913.16.2.12.3.1.3
		snmpManagerAddress OBJECT-TYPE
			SYNTAX DisplayString
			MAX-ACCESS read-write
			STATUS current
			DESCRIPTION
				"SNMP manager IP address. The format should be xxx.xxx.xxx.xxx."
			::= { snmpManagerEntry 3 }


		-- 1.3.6.1.4.1.43913.16.2.12.3.1.4
		snmpManagerEngineID OBJECT-TYPE
			SYNTAX DisplayString
			MAX-ACCESS read-write
			STATUS current
			DESCRIPTION
				"The SNMP management engineID. The format should be 0xDDDDDDDDDDDDDDDD, and minimum length is 14 and
				maximum length is 32 (including 0x as prefix) and should be even."
			::= { snmpManagerEntry 4 }


		-- 1.3.6.1.4.1.43913.16.2.12.3.1.5
		snmpManagerRowStatus OBJECT-TYPE
			SYNTAX RowStatus
			MAX-ACCESS read-write
			STATUS current
			DESCRIPTION
				"The row status of SNMP manager table to control row actions. It has the following actions:

				The status column has six defined values:

				     - `active(1)', which indicates that the conceptual row is
				     available for use by the managed device;

				     - `notInService(2)', which indicates that the conceptual
				     row exists in the agent, but is unavailable for use by
				     the managed device (see NOTE below);

				     - `notReady(3)', which indicates that the conceptual row
				     exists in the agent, but is missing information
				     necessary in order to be available for use by the
				     managed device;

				     - `createAndGo(4)', which is supplied by a management
				     station wishing to create a new instance of a
				     conceptual row and to have its status automatically set
				     to active, making it available for use by the managed
				     device;

				     - `createAndWait(5)', which is supplied by a management
				     station wishing to create a new instance of a
				     conceptual row (but not make it available for use by
				     the managed device); and,

				     - `destroy(6)', which is supplied by a management station
				     wishing to delete all of the instances associated with
				     an existing conceptual row.
				"
			::= { snmpManagerEntry 5 }


		-- 1.3.6.1.4.1.43913.16.2.12.4
		trapUserTable OBJECT-TYPE
			SYNTAX SEQUENCE OF TrapUserEntry
			MAX-ACCESS not-accessible
			STATUS current
			DESCRIPTION
				"Trap/Notification user setup. The trap user name should be only for SNMP v3 notification.
				This table's row only can be added or deleted. The existing row can not be modified."
			::= { snmp 4 }


		-- 1.3.6.1.4.1.43913.16.2.12.4.1
		trapUserEntry OBJECT-TYPE
			SYNTAX TrapUserEntry
			MAX-ACCESS not-accessible
			STATUS current
			DESCRIPTION
				"Trap/Notification setup entry."
			INDEX { trapUserIndex }
			::= { trapUserTable 1 }


		TrapUserEntry ::=
			SEQUENCE {
				trapUserIndex
					Integer32,
				trapUserName
					DisplayString,
				trapUserType
					V3UserType,
				trapUserAuthKey
					DisplayString,
				trapUserPrivateKey
					DisplayString,
				trapUserRowStatus
					RowStatus
			 }

		-- 1.3.6.1.4.1.43913.16.2.12.4.1.1
		trapUserIndex OBJECT-TYPE
			SYNTAX Integer32 (1..10)
			MAX-ACCESS not-accessible
			STATUS current
			DESCRIPTION
				"A unique value for trapTable entry. This value ranges should be from 1 to 10."
			::= { trapUserEntry 1 }


		-- 1.3.6.1.4.1.43913.16.2.12.4.1.2
		trapUserName OBJECT-TYPE
			SYNTAX DisplayString
			MAX-ACCESS read-write
			STATUS current
			DESCRIPTION
				"The trap user name. The max length of trap user name is 20 characters.
				Only alphanumeric characters and chars {- , _} are acceptable.  Leading characters can't be (- or _)."
			::= { trapUserEntry 2 }


		-- 1.3.6.1.4.1.43913.16.2.12.4.1.3
		trapUserType OBJECT-TYPE
			SYNTAX V3UserType
			MAX-ACCESS read-write
			STATUS current
			DESCRIPTION
				"Trap User type is defined as the follow types:
				1--	snmpNoauth,
				2--	snmpmd5,
				3--	snmpsha,
				4--	snmpmd5des,
				5--	snmpmd5aes,
				6--	snmpshades,
				7--	snmpshaaes.
				"
			::= { trapUserEntry 3 }


		-- 1.3.6.1.4.1.43913.16.2.12.4.1.4
		trapUserAuthKey OBJECT-TYPE
			SYNTAX DisplayString
			MAX-ACCESS read-write
			STATUS current
			DESCRIPTION
				"Trap user authentication key. The max length is 32 characters.
				Only chars {a-z,A-Z,0-9, ! ( ) - _ . ? ~ * @ ^ + = : / %} are acceptable. Minimum key length is 8 chars."
			::= { trapUserEntry 4 }


		-- 1.3.6.1.4.1.43913.16.2.12.4.1.5
		trapUserPrivateKey OBJECT-TYPE
			SYNTAX DisplayString
			MAX-ACCESS read-write
			STATUS current
			DESCRIPTION
				"Trap user's private key. The max length is 32 characters.
				Only chars {a-z,A-Z,0-9, ! ( ) - _ . ? ~ * @ ^ + = : / %} are acceptable. Minimum key length is 8 chars."
			::= { trapUserEntry 5 }


		-- 1.3.6.1.4.1.43913.16.2.12.4.1.6
		trapUserRowStatus OBJECT-TYPE
			SYNTAX RowStatus
			MAX-ACCESS read-write
			STATUS current
			DESCRIPTION
				"Trap User Row Status to control row actions. It has the following actions:
				The status column has six defined values:

				     - `active(1)', which indicates that the conceptual row is
				     available for use by the managed device;

				     - `notInService(2)', which indicates that the conceptual
				     row exists in the agent, but is unavailable for use by
				     the managed device (see NOTE below);

				     - `notReady(3)', which indicates that the conceptual row
				     exists in the agent, but is missing information
				     necessary in order to be available for use by the
				     managed device;

				     - `createAndGo(4)', which is supplied by a management
				     station wishing to create a new instance of a
				     conceptual row and to have its status automatically set
				     to active, making it available for use by the managed
				     device;

				     - `createAndWait(5)', which is supplied by a management
				     station wishing to create a new instance of a
				     conceptual row (but not make it available for use by
				     the managed device); and,

				     - `destroy(6)', which is supplied by a management station
				     wishing to delete all of the instances associated with
				     an existing conceptual row.
				"
			::= { trapUserEntry 6 }


		-- 1.3.6.1.4.1.43913.16.2.13
		upgrade OBJECT IDENTIFIER ::= { administration 13 }


		-- 1.3.6.1.4.1.43913.16.2.13.1
		upgradeTable OBJECT-TYPE
			SYNTAX SEQUENCE OF UpgradeEntry
			MAX-ACCESS not-accessible
			STATUS current
			DESCRIPTION
				"This table is used to upgrade firmware for SM2000-5G."
			::= { upgrade 1 }


		-- 1.3.6.1.4.1.43913.16.2.13.1.1
		upgradeEntry OBJECT-TYPE
			SYNTAX UpgradeEntry
			MAX-ACCESS not-accessible
			STATUS current
			DESCRIPTION
				"The entry of the table."
			INDEX { upgradeIndex }
			::= { upgradeTable 1 }


		UpgradeEntry ::=
			SEQUENCE {
				upgradeIndex
					Integer32,
				upgradeModule
					DisplayString,
				upgradeCmd
					DisplayString
			 }

		-- 1.3.6.1.4.1.43913.16.2.13.1.1.1
		upgradeIndex OBJECT-TYPE
			SYNTAX Integer32 (1..5)
			MAX-ACCESS not-accessible
			STATUS current
			DESCRIPTION
				"The index of the table."
			::= { upgradeEntry 1 }


		-- 1.3.6.1.4.1.43913.16.2.13.1.1.2
		upgradeModule OBJECT-TYPE
			SYNTAX DisplayString
			MAX-ACCESS read-only
			STATUS current
			DESCRIPTION
				"The module name."
			::= { upgradeEntry 2 }


		-- 1.3.6.1.4.1.43913.16.2.13.1.1.3
		upgradeCmd OBJECT-TYPE
			SYNTAX DisplayString
			MAX-ACCESS read-write
			STATUS current
			DESCRIPTION
				"The upgrade command, the format should be:file_name,[protocol:]server_ip,user,passwd."
			::= { upgradeEntry 3 }


		-- 1.3.6.1.4.1.43913.16.2.13.2
		upgradeStatusTable OBJECT-TYPE
			SYNTAX SEQUENCE OF UpgradeStatusEntry
			MAX-ACCESS not-accessible
			STATUS current
			DESCRIPTION
				"This table is used to get upgrade status."
			::= { upgrade 2 }


		-- 1.3.6.1.4.1.43913.16.2.13.2.1
		upgradeStatusEntry OBJECT-TYPE
			SYNTAX UpgradeStatusEntry
			MAX-ACCESS not-accessible
			STATUS current
			DESCRIPTION
				"The entry of the table."
			INDEX { upgradeStatusIndex }
			::= { upgradeStatusTable 1 }


		UpgradeStatusEntry ::=
			SEQUENCE {
				upgradeStatusIndex
					Integer32,
				upgradeStatusModule
					DisplayString,
				upgradeStatus
					UpgradeStatus
			 }

		-- 1.3.6.1.4.1.43913.16.2.13.2.1.1
		upgradeStatusIndex OBJECT-TYPE
			SYNTAX Integer32 (1..5)
			MAX-ACCESS not-accessible
			STATUS current
			DESCRIPTION
				"The index of the table."
			::= { upgradeStatusEntry 1 }


		-- 1.3.6.1.4.1.43913.16.2.13.2.1.2
		upgradeStatusModule OBJECT-TYPE
			SYNTAX DisplayString
			MAX-ACCESS read-only
			STATUS current
			DESCRIPTION
				"The module name."
			::= { upgradeStatusEntry 2 }


		-- 1.3.6.1.4.1.43913.16.2.13.2.1.3
		upgradeStatus OBJECT-TYPE
			SYNTAX UpgradeStatus
			MAX-ACCESS read-only
			STATUS current
			DESCRIPTION
				"The status of upgrade:
				0--	No upgrade performed since boot up,
				1--	Retrieving file,
				2--	Retrieving file failed,
				3--	Updating flash,
				4--	Updating flash failed,
				5--	Updating package error,
				6--	Upgrade complete.
				"
			::= { upgradeStatusEntry 3 }


		-- 1.3.6.1.4.1.43913.16.2.14
		pingTest OBJECT IDENTIFIER ::= { administration 14 }


		-- 1.3.6.1.4.1.43913.16.2.14.1
		pingTestTable OBJECT-TYPE
			SYNTAX SEQUENCE OF PingTestEntry
			MAX-ACCESS not-accessible
			STATUS current
			DESCRIPTION
				"This table is used to test ping."
			::= { pingTest 1 }


		-- 1.3.6.1.4.1.43913.16.2.14.1.1
		pingTestEntry OBJECT-TYPE
			SYNTAX PingTestEntry
			MAX-ACCESS not-accessible
			STATUS current
			DESCRIPTION
				"The entry of the table."
			INDEX { pingTestShelfIndex }
			::= { pingTestTable 1 }


		PingTestEntry ::=
			SEQUENCE {
				pingTestShelfIndex
					Integer32,
				pingTestSlotIndex
					Integer32,
				pingTestPortIndex
					Integer32,
				pingTestIpaddr
					DisplayString,
				pingTestResult
					Integer32
			 }

		-- 1.3.6.1.4.1.43913.16.2.14.1.1.1
		pingTestShelfIndex OBJECT-TYPE
			SYNTAX Integer32 (0..4)
			MAX-ACCESS read-only
			STATUS current
			DESCRIPTION
				"The index of the shelf, 0:main shelf; 1~4:expand shelf"
			::= { pingTestEntry 1 }


		-- 1.3.6.1.4.1.43913.16.2.13.1.1.2
		pingTestSlotIndex OBJECT-TYPE
			SYNTAX Integer32 (0..14)
			MAX-ACCESS read-only
			STATUS current
			DESCRIPTION
				"The index of the slot, 0:main shelf; 1~14:slot"
			::= { pingTestEntry 2 }

		-- 1.3.6.1.4.1.43913.16.2.13.1.1.3
		pingTestPortIndex OBJECT-TYPE
			SYNTAX Integer32 (1..4)
			MAX-ACCESS read-only
			STATUS current
			DESCRIPTION
				"The port index of the slot."
			::= { pingTestEntry 3 }


		-- 1.3.6.1.4.1.43913.16.2.14.1.1.4
		pingTestIpaddr OBJECT-TYPE
			SYNTAX DisplayString
			MAX-ACCESS read-write
			STATUS current
			DESCRIPTION
				"The ipv4 or ipv6 address ."
			::= { pingTestEntry 4 }

		-- 1.3.6.1.4.1.43913.16.2.14.1.1.54
		pingTestResult OBJECT-TYPE
			SYNTAX Integer32
			MAX-ACCESS read-only
			STATUS current
			DESCRIPTION
				"The ping result: success(1), fail(2) ."
			::= { pingTestEntry 5 }


		-- 1.3.6.1.4.1.43913.16.2.15
		authNotifyElements OBJECT IDENTIFIER ::= { administration 15 }


		-- 1.3.6.1.4.1.43913.16.2.15.1
		authStatus OBJECT-TYPE
			SYNTAX DisplayString
			MAX-ACCESS read-only
			STATUS current
			DESCRIPTION
				"authentication status."
			::= { authNotifyElements 1 }


		-- 1.3.6.1.4.1.43913.16.2.16
		sm2000AuthFailure NOTIFICATION-TYPE
			OBJECTS { authStatus }
			STATUS current
			DESCRIPTION
				"SM2000-5G authentication failure trap"
			::= { administration 16 }


		-- 1.3.6.1.4.1.43913.16.3
		general OBJECT IDENTIFIER ::= { sm2000-5g 3 }

		-- 1.3.6.1.4.1.43913.16.3.2
		systemTime OBJECT-TYPE
			SYNTAX DisplayString
			MAX-ACCESS read-write
			STATUS current
			DESCRIPTION
				"The date and time of MC module. The setting format of date and time is: YYYY-MM-DD,HH:MM:SS."
			::= { general 2 }


		-- 1.3.6.1.4.1.43913.16.3.3
		leapSecond OBJECT-TYPE
			SYNTAX Integer32
			MAX-ACCESS read-write
			STATUS current
			DESCRIPTION
				"The accumulated leap seconds between TAI and UTC time."
			::= { general 3 }


		-- 1.3.6.1.4.1.43913.16.3.4
		messageGenerate OBJECT-TYPE
			SYNTAX ActionApply
			MAX-ACCESS read-write
			STATUS current
			DESCRIPTION
				"The flag is defined as to generate all messages. For messages that specify a port, only one message will be
				generated instead of a message for all possible ports. This item is write-only."
			::= { general 4 }


		-- 1.3.6.1.4.1.43913.16.3.5
		sync OBJECT-TYPE
			SYNTAX ActionApply
			MAX-ACCESS read-write
			STATUS current
			DESCRIPTION
				"Sync phase and time to current reference. This item is write-only. A read of this item is invalid. Please select apply(1)."
			::= { general 5 }


		-- 1.3.6.1.4.1.43913.16.3.6
		autoSyncConfig OBJECT-TYPE
			SYNTAX ActionState
			MAX-ACCESS read-write
			STATUS current
			DESCRIPTION
				"The auto sync state: enable(1) or disable(0)."
			::= { general 6 }


		-- 1.3.6.1.4.1.43913.16.3.10
		refCriteriaConfig OBJECT-TYPE
			SYNTAX RefCriteria
			MAX-ACCESS read-write
			STATUS current
			DESCRIPTION
				"The reference criteria: manual(0), priority(1) and ssm(2)."
			::= { general 10 }

        -- 1.3.6.1.4.1.43913.16.3.11
		portLinkStatus OBJECT-TYPE
			SYNTAX DisplayString
			MAX-ACCESS read-only
			STATUS current
			DESCRIPTION
				"The port link status (180bytes)
				bytes0~19 : slot1;
				bytes20~39: slot2;
				......
				bytes160~179: slot9
				Valid only for ptp and ntp cards.
				When the ptp card is used,the first four bytes are the port link status.
				ptp card:
				byte[0]=port1Link, byte[1]=port2Link, byte[2]=port3Link, byte[3]=port4Link
				When the ntp card is used,the first five bytes are the port link status.
				ntp card:
				byte[0]=port1Link, byte[1]=port2Link, byte[2]=port3Link, byte[3]=port4Link
				byte[4]=port5Link
				"
			::= { general 11 }

		-- 1.3.6.1.4.1.43913.16.3.12
		refManSrcConfig OBJECT-TYPE
			SYNTAX RefManSrc
			MAX-ACCESS read-write
			STATUS current
			DESCRIPTION
				"The manual reference."
			::= { general 12 }


		-- 1.3.6.1.4.1.43913.16.3.7
		refManFreqSrcConfig OBJECT-TYPE
			SYNTAX RefManFreqSrc
			MAX-ACCESS read-write
			STATUS current
			DESCRIPTION
				"The manual frequency reference."
			::= { general 7 }


		-- 1.3.6.1.4.1.43913.16.3.24
		eprtcMode OBJECT-TYPE
			SYNTAX ActionState
			MAX-ACCESS read-write
			STATUS current
			DESCRIPTION
				"The eprtc mode config."
			::= { general 24 }


		-- 1.3.6.1.4.1.43913.16.3.25
		eprtcSrc OBJECT-TYPE
			SYNTAX Integer32
			MAX-ACCESS read-write
			STATUS current
			DESCRIPTION
				"The eprtc source config. 0 - 10M-1, 1 - 10M-2"
			::= { general 25 }


		-- 1.3.6.1.4.1.43913.16.3.13
		systemStatus OBJECT IDENTIFIER ::= { general 13 }


		-- 1.3.6.1.4.1.43913.16.3.13.1
		generalStatusTable OBJECT-TYPE
			SYNTAX SEQUENCE OF GeneralStatusEntry
			MAX-ACCESS not-accessible
			STATUS current
			DESCRIPTION
				"The system general status table."
			::= { systemStatus 1 }


		-- 1.3.6.1.4.1.43913.16.3.13.1.1
		generalStatusEntry OBJECT-TYPE
			SYNTAX GeneralStatusEntry
			MAX-ACCESS not-accessible
			STATUS current
			DESCRIPTION
				"The entry of system general status table."
			INDEX { generalStatusIndex }
			::= { generalStatusTable 1 }


		GeneralStatusEntry ::=
			SEQUENCE {
				generalStatusIndex
					Integer32,
				systemName
					DisplayString,
				mcTime
					DisplayString,
				mcUpTime
					DisplayString,
				cc1WarmupStatus
					DisplayString,
				cc1State
					DisplayString,
				cc1UpTime
					DisplayString,
				cc2WarmupStatus
					DisplayString,
				cc2State
					DisplayString,
				cc2UpTime
					DisplayString,
				refMode
					DisplayString,
				refInput
					DisplayString,
				clockStatus
					DisplayString,
				phaseOffset
					DisplayString,
				activeAlarms
					Integer32,
				cardLedStatus
					DisplayString,
			    sysCpuLoad
			    	DisplayString,
			    sysMemLoad
			    	DisplayString,
			    cardLedOtherStatus
					OCTET STRING
			 }

		-- 1.3.6.1.4.1.43913.16.3.13.1.1.1
		generalStatusIndex OBJECT-TYPE
			SYNTAX Integer32 (1)
			MAX-ACCESS not-accessible
			STATUS current
			DESCRIPTION
				"The index of system general status table."
			::= { generalStatusEntry 1 }


		-- 1.3.6.1.4.1.43913.16.3.13.1.1.2
		systemName OBJECT-TYPE
			SYNTAX DisplayString
			MAX-ACCESS read-only
			STATUS current
			DESCRIPTION
				"The name of the system."
			::= { generalStatusEntry 2 }


		-- 1.3.6.1.4.1.43913.16.3.13.1.1.3
		mcTime OBJECT-TYPE
			SYNTAX DisplayString
			MAX-ACCESS read-only
			STATUS current
			DESCRIPTION
				"The date and time is UTC time in the system."
			::= { generalStatusEntry 3 }


		-- 1.3.6.1.4.1.43913.16.3.13.1.1.4
		mcUpTime OBJECT-TYPE
			SYNTAX DisplayString
			MAX-ACCESS read-only
			STATUS current
			DESCRIPTION
				"The MC uptime is defined as the length of time since the MC booted."
			::= { generalStatusEntry 4 }


		-- 1.3.6.1.4.1.43913.16.3.13.1.1.5
		cc1WarmupStatus OBJECT-TYPE
			SYNTAX DisplayString
			MAX-ACCESS read-only
			STATUS current
			DESCRIPTION
				"The CC1 warmup status."
			::= { generalStatusEntry 5 }


		-- 1.3.6.1.4.1.43913.16.3.13.1.1.6
		cc1State OBJECT-TYPE
			SYNTAX DisplayString
			MAX-ACCESS read-only
			STATUS current
			DESCRIPTION
				"The CC1 state."
			::= { generalStatusEntry 6 }


		-- 1.3.6.1.4.1.43913.16.3.13.1.1.7
		cc1UpTime OBJECT-TYPE
			SYNTAX DisplayString
			MAX-ACCESS read-only
			STATUS current
			DESCRIPTION
				"The CC1 uptime is defined as the length of time since the CC1 booted."
			::= { generalStatusEntry 7 }


		-- 1.3.6.1.4.1.43913.16.3.13.1.1.8
		cc2WarmupStatus OBJECT-TYPE
			SYNTAX DisplayString
			MAX-ACCESS read-only
			STATUS current
			DESCRIPTION
				"The CC2 warmup status."
			::= { generalStatusEntry 8 }


		-- 1.3.6.1.4.1.43913.16.3.13.1.1.9
		cc2State OBJECT-TYPE
			SYNTAX DisplayString
			MAX-ACCESS read-only
			STATUS current
			DESCRIPTION
				"The CC2 state."
			::= { generalStatusEntry 9 }


		-- 1.3.6.1.4.1.43913.16.3.13.1.1.10
		cc2UpTime OBJECT-TYPE
			SYNTAX DisplayString
			MAX-ACCESS read-only
			STATUS current
			DESCRIPTION
				"The CC2 uptime is defined as the length of time since the CC2 booted."
			::= { generalStatusEntry 10 }


		-- 1.3.6.1.4.1.43913.16.3.13.1.1.11
		refMode OBJECT-TYPE
			SYNTAX DisplayString
			MAX-ACCESS read-only
			STATUS current
			DESCRIPTION
				"The system reference mode."
			::= { generalStatusEntry 11 }


		-- 1.3.6.1.4.1.43913.16.3.13.1.1.12
		refInput OBJECT-TYPE
			SYNTAX DisplayString
			MAX-ACCESS read-only
			STATUS current
			DESCRIPTION
				"The current system reference."
			::= { generalStatusEntry 12 }


		-- 1.3.6.1.4.1.43913.16.3.13.1.1.13
		clockStatus OBJECT-TYPE
			SYNTAX DisplayString
			MAX-ACCESS read-only
			STATUS current
			DESCRIPTION
				"The system clock status."
			::= { generalStatusEntry 13 }


		-- 1.3.6.1.4.1.43913.16.3.13.1.1.14
		phaseOffset OBJECT-TYPE
			SYNTAX DisplayString
			MAX-ACCESS read-only
			STATUS current
			DESCRIPTION
				"The Phase offset in ns between reference and output, only applicable in GPS/GNSS mode."
			::= { generalStatusEntry 14 }


		-- 1.3.6.1.4.1.43913.16.3.13.1.1.17
		activeAlarms OBJECT-TYPE
			SYNTAX Integer32
			MAX-ACCESS read-only
			STATUS current
			DESCRIPTION
				"The total active alarm number of the system."
			::= { generalStatusEntry 17 }
		-- 1.3.6.1.4.1.43913.16.3.13.1.1.18
		cardLedStatus OBJECT-TYPE
			SYNTAX DisplayString
			MAX-ACCESS read-only
			STATUS current
			DESCRIPTION
				"The led status of all card.
				data format:
				Clock1Clock2MgmInput1Input2Output3...Output9
				card type define:
				0: no card, 1: clock card, 2: mgm card, 3: input card, 4: freq out card,
				5: E1 out card, 6: NTP out card, 7: PTP out card, 9: PPS-TOD card,
				a: fiber out card, b: 10GE out card
				led status define:
				0: off, 1: red, 2: green, 3: blink green, 4: yellow, 5: blink red, 6: blink yellow
				clock card data define, 5 bytes:
				cardType,freeRun,activeUse,lock,alarm
				mgm card data define, 5 bytes:
				cardType,powerA,powerB,sys,alarm
				input card data define, 7 bytes:
				cardType,sys,gnss/pps-tod,input1,input2,input3,input4
				out card data define, 3 bytes:
				cardType,power,sys
				NTP out card data define, 7 bytes:
				cardType,power,sys,port1Link,port2Link,port3Link,port4Link
				"
		  ::= { generalStatusEntry 18 }
       -- 1.3.6.1.4.1.43913.16.3.13.1.1.19
		sysCpuLoad OBJECT-TYPE
			SYNTAX DisplayString
			MAX-ACCESS read-only
			STATUS current
			DESCRIPTION
				"The CPU load (%) of the system ."
			::= { generalStatusEntry 19 }

		-- 1.3.6.1.4.1.43913.16.3.13.1.1.20
		sysMemLoad OBJECT-TYPE
			SYNTAX DisplayString
			MAX-ACCESS read-only
			STATUS current
			DESCRIPTION
				"The Memory load (%) of the system ."
			::= { generalStatusEntry 20 }

		-- 1.3.6.1.4.1.43913.16.3.13.1.1.18
		cardLedOtherStatus OBJECT-TYPE
			SYNTAX OCTET STRING
			MAX-ACCESS read-only
			STATUS current
			DESCRIPTION
				"The led other status of all card. Length:90 Byte.
				10 bytes per card.
				Valid only for ptp/10GE/ntp cards.
				When the ptp/10GE card is used,the first five bytes are the port data.
				ptp/10GE card:
				cardType,port1Link,port2Link,port3Link,port4Link
				When the ntp card is used,the first five bytes are the port data.
				ntp card:
				port1Link,port2Link,port3Link,port4Link,port5Link
				"
		  ::= { generalStatusEntry 21 }


		-- 1.3.6.1.4.1.43913.16.3.13.2
		mcHwStatusTable OBJECT-TYPE
			SYNTAX SEQUENCE OF McHwStatusEntry
			MAX-ACCESS not-accessible
			STATUS current
			DESCRIPTION
				"The MC HW status table."
			::= { systemStatus 2 }


		-- 1.3.6.1.4.1.43913.16.3.13.2.1
		mcHwStatusEntry OBJECT-TYPE
			SYNTAX McHwStatusEntry
			MAX-ACCESS not-accessible
			STATUS current
			DESCRIPTION
				"The entry of MC HW status table."
			INDEX { mcHwStatusIndex }
			::= { mcHwStatusTable 1 }


		McHwStatusEntry ::=
			SEQUENCE {
				mcHwStatusIndex
					Integer32,
				mcNeg48vA
					DisplayString,
				mcNeg48vB
					DisplayString,
				mcPos1P2v
					DisplayString,
				mcPos1P8v
					DisplayString,
				mcPos2P5v
					DisplayString,
				mcPos5P5v
					DisplayString,
				mcVCXO
					DisplayString,
				mcFPGA
					DisplayString
			 }

		-- 1.3.6.1.4.1.43913.16.3.13.2.1.1
		mcHwStatusIndex OBJECT-TYPE
			SYNTAX Integer32 (1)
			MAX-ACCESS not-accessible
			STATUS current
			DESCRIPTION
				"The index of MC HW status table."
			::= { mcHwStatusEntry 1 }


		-- 1.3.6.1.4.1.43913.16.3.13.2.1.2
		mcNeg48vA OBJECT-TYPE
			SYNTAX DisplayString
			MAX-ACCESS read-only
			STATUS current
			DESCRIPTION
				"The status of -48V-A voltage."
			::= { mcHwStatusEntry 2 }


		-- 1.3.6.1.4.1.43913.16.3.13.2.1.3
		mcNeg48vB OBJECT-TYPE
			SYNTAX DisplayString
			MAX-ACCESS read-only
			STATUS current
			DESCRIPTION
				"The status of -48V-B voltage."
			::= { mcHwStatusEntry 3 }


		-- 1.3.6.1.4.1.43913.16.3.13.2.1.4
		mcPos1P2v OBJECT-TYPE
			SYNTAX DisplayString
			MAX-ACCESS read-only
			STATUS current
			DESCRIPTION
				"The voltage of +1.2V."
			::= { mcHwStatusEntry 4 }


		-- 1.3.6.1.4.1.43913.16.3.13.2.1.5
		mcPos1P8v OBJECT-TYPE
			SYNTAX DisplayString
			MAX-ACCESS read-only
			STATUS current
			DESCRIPTION
				"The voltage of +1.8V."
			::= { mcHwStatusEntry 5 }


		-- 1.3.6.1.4.1.43913.16.3.13.2.1.6
		mcPos2P5v OBJECT-TYPE
			SYNTAX DisplayString
			MAX-ACCESS read-only
			STATUS current
			DESCRIPTION
				"The voltage of +2.5V."
			::= { mcHwStatusEntry 6 }


		-- 1.3.6.1.4.1.43913.16.3.13.2.1.7
		mcPos5P5v OBJECT-TYPE
			SYNTAX DisplayString
			MAX-ACCESS read-only
			STATUS current
			DESCRIPTION
				"The voltage of +5.5V."
			::= { mcHwStatusEntry 7 }


		-- 1.3.6.1.4.1.43913.16.3.13.2.1.8
		mcVCXO OBJECT-TYPE
			SYNTAX DisplayString
			MAX-ACCESS read-only
			STATUS current
			DESCRIPTION
				"The voltage of VCXO."
			::= { mcHwStatusEntry 8 }


		-- 1.3.6.1.4.1.43913.16.3.13.2.1.9
		mcFPGA OBJECT-TYPE
			SYNTAX DisplayString
			MAX-ACCESS read-only
			STATUS current
			DESCRIPTION
				"The status of FPGA."
			::= { mcHwStatusEntry 9 }


		-- 1.3.6.1.4.1.43913.16.3.13.3
		ccHwStatusTable OBJECT-TYPE
			SYNTAX SEQUENCE OF CcHwStatusEntry
			MAX-ACCESS not-accessible
			STATUS current
			DESCRIPTION
				"The CC HW status table."
			::= { systemStatus 3 }


		-- 1.3.6.1.4.1.43913.16.3.13.3.1
		ccHwStatusEntry OBJECT-TYPE
			SYNTAX CcHwStatusEntry
			MAX-ACCESS not-accessible
			STATUS current
			DESCRIPTION
				"The entry of CC HW status table."
			INDEX { ccHwStatusIndex }
			::= { ccHwStatusTable 1 }


		CcHwStatusEntry ::=
			SEQUENCE {
				ccHwStatusIndex
					Integer32,
				ccHwStatusModleID
					DisplayString,
				ccPos1P8v
					DisplayString,
				cc10mEFC
					DisplayString,
				cc20mEFC
					DisplayString,
				cc25mEFC
					DisplayString,
				cc24P5mEFC
					DisplayString,
				cc24P7mEFC
					DisplayString,
				ccOSCCurrent
					DisplayString,
				ccFPGAVCCint
					DisplayString,
				ccFPGAVCCaux
					DisplayString,
				ccFPGATemp
					DisplayString,
				ccFPGATempHigh
					DisplayString,
				ccFPGATempLow
					DisplayString
			 }

		-- 1.3.6.1.4.1.43913.16.3.13.3.1.1
		ccHwStatusIndex OBJECT-TYPE
			SYNTAX Integer32 (1..2)
			MAX-ACCESS not-accessible
			STATUS current
			DESCRIPTION
				"The index of CC HW status table."
			::= { ccHwStatusEntry 1 }


		-- 1.3.6.1.4.1.43913.16.3.13.3.1.2
		ccHwStatusModleID OBJECT-TYPE
			SYNTAX DisplayString
			MAX-ACCESS read-only
			STATUS current
			DESCRIPTION
				"Module ID."
			::= { ccHwStatusEntry 2 }


		-- 1.3.6.1.4.1.43913.16.3.13.3.1.3
		ccPos1P8v OBJECT-TYPE
			SYNTAX DisplayString
			MAX-ACCESS read-only
			STATUS current
			DESCRIPTION
				"The voltage of +1.8V."
			::= { ccHwStatusEntry 3 }


		-- 1.3.6.1.4.1.43913.16.3.13.3.1.4
		cc10mEFC OBJECT-TYPE
			SYNTAX DisplayString
			MAX-ACCESS read-only
			STATUS current
			DESCRIPTION
				"The voltage of 10M EFC."
			::= { ccHwStatusEntry 4 }


		-- 1.3.6.1.4.1.43913.16.3.13.3.1.5
		cc20mEFC OBJECT-TYPE
			SYNTAX DisplayString
			MAX-ACCESS read-only
			STATUS current
			DESCRIPTION
				"The voltage of 20M EFC."
			::= { ccHwStatusEntry 5 }


		-- 1.3.6.1.4.1.43913.16.3.13.3.1.6
		cc25mEFC OBJECT-TYPE
			SYNTAX DisplayString
			MAX-ACCESS read-only
			STATUS current
			DESCRIPTION
				"The voltage of 25M EFC."
			::= { ccHwStatusEntry 6 }


		-- 1.3.6.1.4.1.43913.16.3.13.3.1.7
		cc24P5mEFC OBJECT-TYPE
			SYNTAX DisplayString
			MAX-ACCESS read-only
			STATUS current
			DESCRIPTION
				"The voltage of 24.5M EFC."
			::= { ccHwStatusEntry 7 }


		-- 1.3.6.1.4.1.43913.16.3.13.3.1.8
		cc24P7mEFC OBJECT-TYPE
			SYNTAX DisplayString
			MAX-ACCESS read-only
			STATUS current
			DESCRIPTION
				"The voltage of 24.7M EFC."
			::= { ccHwStatusEntry 8 }


		-- 1.3.6.1.4.1.43913.16.3.13.3.1.9
		ccOSCCurrent OBJECT-TYPE
			SYNTAX DisplayString
			MAX-ACCESS read-only
			STATUS current
			DESCRIPTION
				"OSC current."
			::= { ccHwStatusEntry 9 }


		-- 1.3.6.1.4.1.43913.16.3.13.3.1.10
		ccFPGAVCCint OBJECT-TYPE
			SYNTAX DisplayString
			MAX-ACCESS read-only
			STATUS current
			DESCRIPTION
				"The voltage of FPGA VCCint."
			::= { ccHwStatusEntry 10 }


		-- 1.3.6.1.4.1.43913.16.3.13.3.1.11
		ccFPGAVCCaux OBJECT-TYPE
			SYNTAX DisplayString
			MAX-ACCESS read-only
			STATUS current
			DESCRIPTION
				"The voltage of FPGA VCCaux."
			::= { ccHwStatusEntry 11 }


		-- 1.3.6.1.4.1.43913.16.3.13.3.1.12
		ccFPGATemp OBJECT-TYPE
			SYNTAX DisplayString
			MAX-ACCESS read-only
			STATUS current
			DESCRIPTION
				"FPGA temperature."
			::= { ccHwStatusEntry 12 }


		-- 1.3.6.1.4.1.43913.16.3.13.3.1.13
		ccFPGATempHigh OBJECT-TYPE
			SYNTAX DisplayString
			MAX-ACCESS read-only
			STATUS current
			DESCRIPTION
				"FPGA temperature hight."
			::= { ccHwStatusEntry 13 }


		-- 1.3.6.1.4.1.43913.16.3.13.3.1.14
		ccFPGATempLow OBJECT-TYPE
			SYNTAX DisplayString
			MAX-ACCESS read-only
			STATUS current
			DESCRIPTION
				"FPGA temperature low."
			::= { ccHwStatusEntry 14 }


		-- 1.3.6.1.4.1.43913.16.13.4
		sm2000TrapGeneralStatus NOTIFICATION-TYPE
			OBJECTS { generalStatusIndex, systemName, cc1WarmupStatus, cc1State, cc2WarmupStatus, cc2State, refMode, refInput, clockStatus, phaseOffset, activeAlarms }
			STATUS current
			DESCRIPTION
				"SM2000-5G general status trap object which specifies generalStatusIndex, systemName, cc1WarmupStatus, cc1State, cc2WarmupStatus, cc2State refMode, refInput, clockStatus , phaseOffset, activeAlarms."
			::= { systemStatus 4 }


		-- 1.3.6.1.4.1.43913.16.3.15
		refInfoTable OBJECT-TYPE
			SYNTAX SEQUENCE OF RefInfoEntry
			MAX-ACCESS not-accessible
			STATUS current
			DESCRIPTION
				"The system reference information table."
			::= { general 15 }


		-- 1.3.6.1.4.1.43913.16.3.15.1
		refInfoEntry OBJECT-TYPE
			SYNTAX RefInfoEntry
			MAX-ACCESS not-accessible
			STATUS current
			DESCRIPTION
				"The entry of system reference information table."
			INDEX { refInfoIndex }
			::= { refInfoTable 1 }


		RefInfoEntry ::=
			SEQUENCE {
				refInfoIndex
					Integer32,
				reference
					DisplayString,
				refState
					DisplayString,
				refPriority
					Integer32,
				refQLState
					DisplayString,
				refQLCfgValue
					ClkQL,
				refQLValue
					ClkQL,
				refStatus
					DisplayString
			 }

		-- 1.3.6.1.4.1.43913.16.3.15.1.1
		refInfoIndex OBJECT-TYPE
			SYNTAX Integer32 (1..16)
			MAX-ACCESS not-accessible
			STATUS current
			DESCRIPTION
				"The index of system reference information table."
			::= { refInfoEntry 1 }


		-- 1.3.6.1.4.1.43913.16.3.15.1.2
		reference OBJECT-TYPE
			SYNTAX DisplayString
			MAX-ACCESS read-only
			STATUS current
			DESCRIPTION
				"Reference type."
			::= { refInfoEntry 2 }


		-- 1.3.6.1.4.1.43913.16.3.15.1.3
		refState OBJECT-TYPE
			SYNTAX DisplayString
			MAX-ACCESS read-only
			STATUS current
			DESCRIPTION
				"Reference state."
			::= { refInfoEntry 3 }


		-- 1.3.6.1.4.1.43913.16.3.15.1.4
		refPriority OBJECT-TYPE
			SYNTAX Integer32
			MAX-ACCESS read-only
			STATUS current
			DESCRIPTION
				"Reference priority."
			::= { refInfoEntry 4 }


		-- 1.3.6.1.4.1.43913.16.3.15.1.5
		refQLState OBJECT-TYPE
			SYNTAX DisplayString
			MAX-ACCESS read-only
			STATUS current
			DESCRIPTION
				"QL state."
			::= { refInfoEntry 5 }


		-- 1.3.6.1.4.1.43913.16.3.15.1.6
		refQLCfgValue OBJECT-TYPE
			SYNTAX ClkQL
			MAX-ACCESS read-only
			STATUS current
			DESCRIPTION
				"QL config value."
			::= { refInfoEntry 6 }


		-- 1.3.6.1.4.1.43913.16.3.15.1.7
		refQLValue OBJECT-TYPE
			SYNTAX ClkQL
			MAX-ACCESS read-only
			STATUS current
			DESCRIPTION
				"QL value."
			::= { refInfoEntry 7 }


		-- 1.3.6.1.4.1.43913.16.3.15.1.8
		refStatus OBJECT-TYPE
			SYNTAX DisplayString
			MAX-ACCESS read-only
			STATUS current
			DESCRIPTION
				"Reference status."
			::= { refInfoEntry 8 }


		-- 1.3.6.1.4.1.43913.16.3.16
		ccStateTable OBJECT-TYPE
			SYNTAX SEQUENCE OF CcStateEntry
			MAX-ACCESS not-accessible
			STATUS current
			DESCRIPTION
				"The CC state table to configure the state of CC."
			::= { general 16 }


		-- 1.3.6.1.4.1.43913.16.3.16.1
		ccStateEntry OBJECT-TYPE
			SYNTAX CcStateEntry
			MAX-ACCESS not-accessible
			STATUS current
			DESCRIPTION
				"The CC state table for configuring the state of CC."
			INDEX { ccStateIndex }
			::= { ccStateTable 1 }


		CcStateEntry ::=
			SEQUENCE {
				ccStateIndex
					Integer32,
				ccModuleID
					DisplayString,
				ccState
					CCState,
				ccCPUload
					DisplayString,
				ccMEMload
					DisplayString,
				tempHighTho
					Integer32,
				tempLowTho
					Integer32
			 }

		-- 1.3.6.1.4.1.43913.16.3.16.1.1
		ccStateIndex OBJECT-TYPE
			SYNTAX Integer32 (1..2)
			MAX-ACCESS not-accessible
			STATUS current
			DESCRIPTION
				"CC index: 1~2."
			::= { ccStateEntry 1 }


		-- 1.3.6.1.4.1.43913.16.3.16.1.2
		ccModuleID OBJECT-TYPE
			SYNTAX DisplayString
			MAX-ACCESS read-only
			STATUS current
			DESCRIPTION
				"The CC module ID: CC1, CC2. This field is read-only."
			::= { ccStateEntry 2 }


		-- 1.3.6.1.4.1.43913.16.3.16.1.4
		ccCPUload OBJECT-TYPE
			SYNTAX DisplayString
			MAX-ACCESS read-only
			STATUS current
			DESCRIPTION
				"CC CPU load percentage."
			::= { ccStateEntry 4 }

		-- 1.3.6.1.4.1.43913.16.3.16.1.5
		ccMEMload OBJECT-TYPE
			SYNTAX DisplayString
			MAX-ACCESS read-only
			STATUS current
			DESCRIPTION
				"CC memory load percentage."
			::= { ccStateEntry 5 }

		-- 1.3.6.1.4.1.43913.16.3.16.1.3
		ccState OBJECT-TYPE
			SYNTAX CCState
			MAX-ACCESS read-write
			STATUS current
			DESCRIPTION
				"CC state. The value could be : active(0), standby(1), active warmup(2),
				standby warmup(3), failed(4), disabled(5)."
			::= { ccStateEntry 3 }

		-- 1.3.6.1.4.1.43913.16.3.16.1.6
		tempHighTho OBJECT-TYPE
			SYNTAX Integer32 (-120..120)
			MAX-ACCESS read-write
			STATUS current
			DESCRIPTION
				"Temperature high alarm threshold for clock module."
			::= { ccStateEntry 6 }

		-- 1.3.6.1.4.1.43913.16.3.16.1.7
		tempLowTho OBJECT-TYPE
			SYNTAX Integer32 (-120..120)
			MAX-ACCESS read-write
			STATUS current
			DESCRIPTION
				"Temperature low alarm threshold for clock module."
			::= { ccStateEntry 7 }


		-- 1.3.6.1.4.1.43913.16.3.17
		logFileSettingTable OBJECT-TYPE
			SYNTAX SEQUENCE OF LogFileSettingEntry
			MAX-ACCESS not-accessible
			STATUS current
			DESCRIPTION
				"The log file table is used to configure the log file size and access options."
			::= { general 17 }


		-- 1.3.6.1.4.1.43913.16.3.17.1
		logFileSettingEntry OBJECT-TYPE
			SYNTAX LogFileSettingEntry
			MAX-ACCESS not-accessible
			STATUS current
			DESCRIPTION
				"The log file table to define the buffer size."
			INDEX { logFileSettingIndex }
			::= { logFileSettingTable 1 }


		LogFileSettingEntry ::=
			SEQUENCE {
				logFileSettingIndex
					Integer32,
				logFileTypeName
					DisplayString,
				logFileBufferSize
					Unsigned32,
				logFileAccessOpt
					DisplayString
			 }

		-- 1.3.6.1.4.1.43913.16.3.17.1.1
		logFileSettingIndex OBJECT-TYPE
			SYNTAX Integer32 (1..4)
			MAX-ACCESS not-accessible
			STATUS current
			DESCRIPTION
				"The index of log file table."
			::= { logFileSettingEntry 1 }


		-- 1.3.6.1.4.1.43913.16.3.17.1.2
		logFileTypeName OBJECT-TYPE
			SYNTAX DisplayString
			MAX-ACCESS read-only
			STATUS current
			DESCRIPTION
				"The log type name. This item is read only. It has the following names: Alarm, Event, Command, Security."
			::= { logFileSettingEntry 2 }


		-- 1.3.6.1.4.1.43913.16.3.17.1.3
		logFileBufferSize OBJECT-TYPE
			SYNTAX Unsigned32
			MAX-ACCESS read-write
			STATUS current
			DESCRIPTION
				"The size for the log file.  The max value is 100 KB."
			::= { logFileSettingEntry 3 }


		-- 1.3.6.1.4.1.43913.16.3.17.1.4
		logFileAccessOpt OBJECT-TYPE
			SYNTAX DisplayString
			MAX-ACCESS read-write
			STATUS current
			DESCRIPTION
				"Access options for log files. format: index,direction,lines
				index: 0-6, default is 0, the latest log file.
				direciton: head/tail, default is tail.
				lines: max is 500, default is 20."
			::= { logFileSettingEntry 4 }


		-- 1.3.6.1.4.1.43913.16.3.18
		remoteSyslogTable OBJECT-TYPE
			SYNTAX SEQUENCE OF RemoteSyslogEntry
			MAX-ACCESS not-accessible
			STATUS current
			DESCRIPTION
				"The remote syslog file control table."
			::= { general 18 }


		-- 1.3.6.1.4.1.43913.16.3.18.1
		remoteSyslogEntry OBJECT-TYPE
			SYNTAX RemoteSyslogEntry
			MAX-ACCESS not-accessible
			STATUS current
			DESCRIPTION
				"The entry of remote log file control table."
			INDEX { remoteSyslogIndex }
			::= { remoteSyslogTable 1 }


		RemoteSyslogEntry ::=
			SEQUENCE {
				remoteSyslogIndex
					Integer32,
				remoteSyslogState
					ActionState,
				remoteSyslogAddress
					DisplayString
			 }

		-- 1.3.6.1.4.1.43913.16.3.18.1.1
		remoteSyslogIndex OBJECT-TYPE
			SYNTAX Integer32 (1)
			MAX-ACCESS not-accessible
			STATUS current
			DESCRIPTION
				"The index of remote log file table."
			::= { remoteSyslogEntry 1 }


		-- 1.3.6.1.4.1.43913.16.3.18.1.2
		remoteSyslogState OBJECT-TYPE
			SYNTAX ActionState
			MAX-ACCESS read-write
			STATUS current
			DESCRIPTION
				"The remote syslog state control. The setting could be enable(1), or disable(0)."
			::= { remoteSyslogEntry 2 }


		-- 1.3.6.1.4.1.43913.16.3.18.1.3
		remoteSyslogAddress OBJECT-TYPE
			SYNTAX DisplayString
			MAX-ACCESS read-write
			STATUS current
			DESCRIPTION
				"The IP address of remote syslog machine. The format should be xxx.xxx.xxx.xxx"
			::= { remoteSyslogEntry 3 }


		-- 1.3.6.1.4.1.43913.16.3.20
		ssmQlTable OBJECT-TYPE
			SYNTAX SEQUENCE OF SsmQlEntry
			MAX-ACCESS not-accessible
			STATUS current
			DESCRIPTION
				"The SSM-QL mapping table."
			::= { general 20 }


		-- 1.3.6.1.4.1.43913.16.3.20.1
		ssmQlEntry OBJECT-TYPE
			SYNTAX SsmQlEntry
			MAX-ACCESS not-accessible
			STATUS current
			DESCRIPTION
				"The entry of SSM-QL mapping table."
			INDEX { ssmQlIndex }
			::= { ssmQlTable 1 }


		SsmQlEntry ::=
			SEQUENCE {
				ssmQlIndex
					Integer32,
				ssmValue
					DisplayString,
				clockQL
					DisplayString,
				ptpClkClass
					DisplayString
			 }

		-- 1.3.6.1.4.1.43913.16.3.20.1.1
		ssmQlIndex OBJECT-TYPE
			SYNTAX Integer32 (1..7)
			MAX-ACCESS not-accessible
			STATUS current
			DESCRIPTION
				"The index of SSM-QL mapping table."
			::= { ssmQlEntry 1 }


		-- 1.3.6.1.4.1.43913.16.3.20.1.2
		ssmValue OBJECT-TYPE
			SYNTAX DisplayString
			MAX-ACCESS read-only
			STATUS current
			DESCRIPTION
				"The SSM valye."
			::= { ssmQlEntry 2 }


		-- 1.3.6.1.4.1.43913.16.3.20.1.3
		clockQL OBJECT-TYPE
			SYNTAX DisplayString
			MAX-ACCESS read-only
			STATUS current
			DESCRIPTION
				"The clock quality level."
			::= { ssmQlEntry 3 }


		-- 1.3.6.1.4.1.43913.16.3.20.1.4
		ptpClkClass OBJECT-TYPE
			SYNTAX DisplayString
			MAX-ACCESS read-only
			STATUS current
			DESCRIPTION
				"The PTP clock class."
			::= { ssmQlEntry 4 }

		-- 1.3.6.1.4.1.43913.16.13.21
		sm2000TrapRefinfo NOTIFICATION-TYPE
			OBJECTS { refInfoIndex, reference, refState, refPriority, refQLState, refQLCfgValue, refQLValue, refStatus }
			STATUS current
			DESCRIPTION
				"SM2000-5G reference information trap object which specifies ref index, reference name, ref state, priority, QL-state, QL config value, QL value, status."
			::= { general 21 }

		-- 1.3.6.1.4.1.43913.16.13.22
		sm2000TrapCCstate NOTIFICATION-TYPE
			OBJECTS { ccStateIndex, ccModuleID, ccState }
			STATUS current
			DESCRIPTION
				"SM2000-5G Clock card state trap object which specifies ccStateIndex, moduleID(CC1, CC2), state(0-active, 1-standby, 2-active warmup, 3-standby warmup, 4-failed, 5-disabled)."
			::= { general 22 }

		-- 1.3.6.1.4.1.43913.16.3.23
		refInfoPtpinTable OBJECT-TYPE
			SYNTAX SEQUENCE OF RefInfoPtpinEntry
			MAX-ACCESS not-accessible
			STATUS current
			DESCRIPTION
				"The system reference information table for PTP input card."
			::= { general 23 }


		-- 1.3.6.1.4.1.43913.16.3.23.1
		refInfoPtpinEntry OBJECT-TYPE
			SYNTAX RefInfoPtpinEntry
			MAX-ACCESS not-accessible
			STATUS current
			DESCRIPTION
				"The entry of system reference information table for PTP input card."
			INDEX { refInfoPtpinIndex }
			::= { refInfoPtpinTable 1 }


		RefInfoPtpinEntry ::=
			SEQUENCE {
				refInfoPtpinIndex
					Integer32,
				referencePtpin
					DisplayString,
				refStatePtpin
					DisplayString,
				refPriorityPtpin
					Integer32,
				refStatusPtpin
					DisplayString
			 }

		-- 1.3.6.1.4.1.43913.16.3.23.1.1
		refInfoPtpinIndex OBJECT-TYPE
			SYNTAX Integer32 (1..4)
			MAX-ACCESS not-accessible
			STATUS current
			DESCRIPTION
				"The index of system reference information table for PTP input card."
			::= { refInfoPtpinEntry 1 }


		-- 1.3.6.1.4.1.43913.16.3.23.1.2
		referencePtpin OBJECT-TYPE
			SYNTAX DisplayString
			MAX-ACCESS read-only
			STATUS current
			DESCRIPTION
				"Reference type. PTP1,PTP2,GNSS-1,GNSS-2"
			::= { refInfoPtpinEntry 2 }


		-- 1.3.6.1.4.1.43913.16.3.23.1.3
		refStatePtpin OBJECT-TYPE
			SYNTAX DisplayString
			MAX-ACCESS read-only
			STATUS current
			DESCRIPTION
				"Reference state."
			::= { refInfoPtpinEntry 3 }


		-- 1.3.6.1.4.1.43913.16.3.23.1.4
		refPriorityPtpin OBJECT-TYPE
			SYNTAX Integer32
			MAX-ACCESS read-only
			STATUS current
			DESCRIPTION
				"Reference priority."
			::= { refInfoPtpinEntry 4 }


		-- 1.3.6.1.4.1.43913.16.3.23.1.5
		refStatusPtpin OBJECT-TYPE
			SYNTAX DisplayString
			MAX-ACCESS read-only
			STATUS current
			DESCRIPTION
				"Reference status."
			::= { refInfoPtpinEntry 5 }


		-- 1.3.6.1.4.1.43913.16.4
		gnss OBJECT IDENTIFIER ::= { sm2000-5g 4 }


		-- 1.3.6.1.4.1.43913.16.4.1
		gnss1 OBJECT IDENTIFIER ::= { gnss 1 }
		-- 1.3.6.1.4.1.43913.16.4.1.1
		gnss1State OBJECT-TYPE
			SYNTAX ActionState
			MAX-ACCESS read-write
			STATUS current
			DESCRIPTION
				"Show / Set GNSS-1 state, disable(0), enable(1)."
			::= { gnss1 1 }


		-- 1.3.6.1.4.1.43913.16.4.1.2
		gnss1Mode OBJECT-TYPE
			SYNTAX GPSMode
			MAX-ACCESS read-write
			STATUS current
			DESCRIPTION
				"GNSS-1 operation mode. It is defined as follows: auto(0), manual(1).
				When the auto mode is selected, manually setting gps position is prohibited."
			::= { gnss1 2 }


		-- 1.3.6.1.4.1.43913.16.4.1.3
		gnss1Mask OBJECT-TYPE
			SYNTAX Integer32
			MAX-ACCESS read-write
			STATUS current
			DESCRIPTION
				"Show / Set GNSS-1 mask."
			::= { gnss1 3 }


		-- 1.3.6.1.4.1.43913.16.4.1.4
		gnss1TrackMode OBJECT-TYPE
			SYNTAX TrackMode
			MAX-ACCESS read-write
			STATUS current
			DESCRIPTION
				"Show / Set GNSS-1 track mode."
			::= { gnss1 4 }


		-- 1.3.6.1.4.1.43913.16.4.1.5
		gnss1CableDelay OBJECT-TYPE
			SYNTAX Integer32
			MAX-ACCESS read-write
			STATUS current
			DESCRIPTION
				"Show / Set GNSS-1 cable delay."
			::= { gnss1 5 }


		-- 1.3.6.1.4.1.43913.16.4.1.6
		gnss1Priority OBJECT-TYPE
			SYNTAX Integer32
			MAX-ACCESS read-write
			STATUS current
			DESCRIPTION
				"Show / Set GNSS-1 priority."
			::= { gnss1 6 }


		-- 1.3.6.1.4.1.43913.16.4.1.7
		gnss1PQLState OBJECT-TYPE
			SYNTAX ActionState
			MAX-ACCESS read-write
			STATUS current
			DESCRIPTION
				"Show / Set GNSS-1 PQL state, disable(0), enable(1)."
			::= { gnss1 7 }


		-- 1.3.6.1.4.1.43913.16.4.1.8
		gnss1PQL OBJECT-TYPE
			SYNTAX Integer32
			MAX-ACCESS read-write
			STATUS current
			DESCRIPTION
				"Show / Set GNSS-1 PQL value."
			::= { gnss1 8 }


		-- 1.3.6.1.4.1.43913.16.4.1.9
		gnss1CurrentPosMode OBJECT-TYPE
			SYNTAX GPSPosMode
			MAX-ACCESS read-only
			STATUS current
			DESCRIPTION
				"Show GNSS-1 current position mode, survey(0), hold(1), manual(2)."
			::= { gnss1 9 }


		-- 1.3.6.1.4.1.43913.16.4.1.10
		gnss1CurrentPosition OBJECT-TYPE
			SYNTAX DisplayString
			MAX-ACCESS read-only
			STATUS current
			DESCRIPTION
				"Show GNSS-1 current position. The format is latitude,longitude,hight."
			::= { gnss1 10 }


		-- 1.3.6.1.4.1.43913.16.4.1.11
		gnss1PositionConfig OBJECT-TYPE
			SYNTAX DisplayString
			MAX-ACCESS read-write
			STATUS current
			DESCRIPTION
				"The configuration of GNSS-1 position. The format is latitude,longitude,hight. Before the GNSS-1 position is configured,
				GNSS-1 mode should be setup as manual mode."
			::= { gnss1 11 }


		-- 1.3.6.1.4.1.43913.16.4.1.12
		gnss1SVTable OBJECT-TYPE
			SYNTAX SEQUENCE OF Gnss1SVEntry
			MAX-ACCESS not-accessible
			STATUS current
			DESCRIPTION
				"The tracked satellites table which provides the information about the satellites being tracked."
			::= { gnss1 12 }


		-- 1.3.6.1.4.1.43913.16.4.1.12.1
		gnss1SVEntry OBJECT-TYPE
			SYNTAX Gnss1SVEntry
			MAX-ACCESS not-accessible
			STATUS current
			DESCRIPTION
				"The entry of the satellites being tracked."
			INDEX { gnss1Index }
			::= { gnss1SVTable 1 }


		Gnss1SVEntry ::=
			SEQUENCE {
				gnss1Index
					Integer32,
				gnss1SVNum
					Integer32,
				gnss1SNR
					Integer32,
				gnss1Health
					GPSHealthy,
				gnss1Azimuth
					Integer32,
				gnss1Elevation
					Integer32,
				gnss1Signal
					DisplayString,
				gnss1SatUsed
					DisplayString
			 }

		-- 1.3.6.1.4.1.43913.16.4.1.12.1.1
		gnss1Index OBJECT-TYPE
			SYNTAX Integer32 (1..60)
			MAX-ACCESS not-accessible
			STATUS current
			DESCRIPTION
				"The index of tracked satellites table."
			::= { gnss1SVEntry 1 }


		-- 1.3.6.1.4.1.43913.16.4.1.12.1.2
		gnss1SVNum OBJECT-TYPE
			SYNTAX Integer32
			MAX-ACCESS read-only
			STATUS current
			DESCRIPTION
				"Satellite Vehicle Number - This is the identification number of the satellite being tracked."
			::= { gnss1SVEntry 2 }


		-- 1.3.6.1.4.1.43913.16.4.1.12.1.3
		gnss1SNR OBJECT-TYPE
			SYNTAX Integer32
			MAX-ACCESS read-only
			STATUS current
			DESCRIPTION
				"Signal to Noise Ratio."
			::= { gnss1SVEntry 3 }


		-- 1.3.6.1.4.1.43913.16.4.1.12.1.4
		gnss1Health OBJECT-TYPE
			SYNTAX GPSHealthy
			MAX-ACCESS read-only
			STATUS current
			DESCRIPTION
				"Indicates the health of the satellite. States are as follows: healthy(1), unhealthy(2)."
			::= { gnss1SVEntry 4 }


		-- 1.3.6.1.4.1.43913.16.4.1.12.1.5
		gnss1Azimuth OBJECT-TYPE
			SYNTAX Integer32
			MAX-ACCESS read-only
			STATUS current
			DESCRIPTION
				"Satellites horizontal position measured in degrees clockwise from the north."
			::= { gnss1SVEntry 5 }


		-- 1.3.6.1.4.1.43913.16.4.1.12.1.6
		gnss1Elevation OBJECT-TYPE
			SYNTAX Integer32
			MAX-ACCESS read-only
			STATUS current
			DESCRIPTION
				"Vertical position of satellite in degrees from the horizon."
			::= { gnss1SVEntry 6 }


		-- 1.3.6.1.4.1.43913.16.4.1.12.1.7
		gnss1Signal OBJECT-TYPE
			SYNTAX DisplayString
			MAX-ACCESS read-only
			STATUS current
			DESCRIPTION
				"SAT signal. Unknown,L1CA,L2CL,L2CM,B1D1,B1D2,B2D1,B2D2"
			::= { gnss1SVEntry 7 }


		-- 1.3.6.1.4.1.43913.16.4.1.12.1.8
		gnss1SatUsed OBJECT-TYPE
			SYNTAX DisplayString
			MAX-ACCESS read-only
			STATUS current
			DESCRIPTION
				"SAT used flag. Yes or No"
			::= { gnss1SVEntry 8}


		-- 1.3.6.1.4.1.43913.16.4.1.13
		gnss1InfoTable OBJECT-TYPE
			SYNTAX SEQUENCE OF Gnss1InfoEntry
			MAX-ACCESS not-accessible
			STATUS current
			DESCRIPTION
				"The GNSS-1 engine infomation table."
			::= { gnss1 13 }


		-- 1.3.6.1.4.1.43913.16.4.1.13.1
		gnss1InfoEntry OBJECT-TYPE
			SYNTAX Gnss1InfoEntry
			MAX-ACCESS not-accessible
			STATUS current
			DESCRIPTION
				"The entry of GNSS-1 engine infomation table."
			INDEX { gnss1InfoIndex }
			::= { gnss1InfoTable 1 }


		Gnss1InfoEntry ::=
			SEQUENCE {
				gnss1InfoIndex
					Integer32,
				gnss1InfoVendor
					DisplayString,
				gnss1InfoName
					DisplayString,
				gnss1InfoSWVer
					DisplayString,
				gnss1InfoHWVer
					DisplayString
			 }

		-- 1.3.6.1.4.1.43913.16.4.1.13.1.1
		gnss1InfoIndex OBJECT-TYPE
			SYNTAX Integer32 (1)
			MAX-ACCESS not-accessible
			STATUS current
			DESCRIPTION
				"The index of GNSS-1 engine infomation table."
			::= { gnss1InfoEntry 1 }


		-- 1.3.6.1.4.1.43913.16.4.1.13.1.2
		gnss1InfoVendor OBJECT-TYPE
			SYNTAX DisplayString
			MAX-ACCESS read-only
			STATUS current
			DESCRIPTION
				"The vendor if GNSS-1 engine."
			::= { gnss1InfoEntry 2 }


		-- 1.3.6.1.4.1.43913.16.4.1.13.1.3
		gnss1InfoName OBJECT-TYPE
			SYNTAX DisplayString
			MAX-ACCESS read-only
			STATUS current
			DESCRIPTION
				"The product name of GNSS-1 engine."
			::= { gnss1InfoEntry 3 }


		-- 1.3.6.1.4.1.43913.16.4.1.13.1.4
		gnss1InfoSWVer OBJECT-TYPE
			SYNTAX DisplayString
			MAX-ACCESS read-only
			STATUS current
			DESCRIPTION
				"The software version of GNSS-1 engine."
			::= { gnss1InfoEntry 4 }


		-- 1.3.6.1.4.1.43913.16.4.1.13.1.5
		gnss1InfoHWVer OBJECT-TYPE
			SYNTAX DisplayString
			MAX-ACCESS read-only
			STATUS current
			DESCRIPTION
				"The hardware version of GNSS-1 engine."
			::= { gnss1InfoEntry 5 }


		-- 1.3.6.1.4.1.43913.16.4.1.14
		gnss1ClockStatuc OBJECT-TYPE
			SYNTAX DisplayString
			MAX-ACCESS read-only
			STATUS current
			DESCRIPTION
				"Show GNSS-1 clock status. "
			::= { gnss1 14 }


		-- 1.3.6.1.4.1.43913.16.4.1.15
		gnss1AeroCorrTable OBJECT-TYPE
			SYNTAX SEQUENCE OF Gnss1AeroCorrEntry
			MAX-ACCESS not-accessible
			STATUS current
			DESCRIPTION
				"The table which provides the information about the satellites aero-correction."
			::= { gnss1 15 }


		-- 1.3.6.1.4.1.43913.16.4.1.15.1
		gnss1AeroCorrEntry OBJECT-TYPE
			SYNTAX Gnss1AeroCorrEntry
			MAX-ACCESS not-accessible
			STATUS current
			DESCRIPTION
				"The entry of the satellites."
			INDEX { gnss1AeroCorrIndex }
			::= { gnss1AeroCorrTable 1 }


		Gnss1AeroCorrEntry ::=
			SEQUENCE {
				gnss1AeroCorrIndex
					Integer32,
				gnss1AeroCorrSVNum
					Integer32,
				gnss1AeroCorrSVType
					SVTYPE,
				gnss1AeroCorrIono
					DisplayString,
				gnss1AeroCorrTropo
					DisplayString
			 }

		-- 1.3.6.1.4.1.43913.16.4.1.15.1.1
		gnss1AeroCorrIndex OBJECT-TYPE
			SYNTAX Integer32 (1..60)
			MAX-ACCESS not-accessible
			STATUS current
			DESCRIPTION
				"The index of tracked satellites table. GPS: 1-30, BD: 31-60"
			::= { gnss1AeroCorrEntry 1 }


		-- 1.3.6.1.4.1.43913.16.4.1.15.1.2
		gnss1AeroCorrSVNum OBJECT-TYPE
			SYNTAX Integer32
			MAX-ACCESS read-only
			STATUS current
			DESCRIPTION
				"Satellite Vehicle Number - This is the identification number of the satellite."
			::= { gnss1AeroCorrEntry 2 }


		-- 1.3.6.1.4.1.43913.16.4.1.15.1.3
		gnss1AeroCorrSVType OBJECT-TYPE
			SYNTAX SVTYPE
			MAX-ACCESS read-only
			STATUS current
			DESCRIPTION
				"BD/GPS Satellite."
			::= { gnss1AeroCorrEntry 3 }


		-- 1.3.6.1.4.1.43913.16.4.1.15.1.4
		gnss1AeroCorrIono OBJECT-TYPE
			SYNTAX DisplayString
			MAX-ACCESS read-only
			STATUS current
			DESCRIPTION
				"SAT iono correction."
			::= { gnss1AeroCorrEntry 4 }


		-- 1.3.6.1.4.1.43913.16.4.1.15.1.5
		gnss1AeroCorrTropo OBJECT-TYPE
			SYNTAX DisplayString
			MAX-ACCESS read-only
			STATUS current
			DESCRIPTION
				"SAT tropo correction."
			::= { gnss1AeroCorrEntry 5 }


		-- 1.3.6.1.4.1.43913.16.4.1.16
		gnss1CoordTable OBJECT-TYPE
			SYNTAX SEQUENCE OF Gnss1CoordEntry
			MAX-ACCESS not-accessible
			STATUS current
			DESCRIPTION
				"The table which provides the information about the satellites coordinate."
			::= { gnss1 16 }


		-- 1.3.6.1.4.1.43913.16.4.1.16.1
		gnss1CoordEntry OBJECT-TYPE
			SYNTAX Gnss1CoordEntry
			MAX-ACCESS not-accessible
			STATUS current
			DESCRIPTION
				"The entry of the satellites."
			INDEX { gnss1CoordIndex }
			::= { gnss1CoordTable 1 }


		Gnss1CoordEntry ::=
			SEQUENCE {
				gnss1CoordIndex
					Integer32,
				gnss1CoordSVNum
					Integer32,
				gnss1CoordSVType
					SVTYPE,
				gnss1CoordX
					DisplayString,
				gnss1CoordY
					DisplayString,
				gnss1CoordZ
					DisplayString,
				gnss1ClkCorr
					DisplayString
			 }

		-- 1.3.6.1.4.1.43913.16.4.1.16.1.1
		gnss1CoordIndex OBJECT-TYPE
			SYNTAX Integer32 (1..60)
			MAX-ACCESS not-accessible
			STATUS current
			DESCRIPTION
				"The index of tracked satellites table. GPS: 1-30, BD: 31-60"
			::= { gnss1CoordEntry 1 }


		-- 1.3.6.1.4.1.43913.16.4.1.16.1.2
		gnss1CoordSVNum OBJECT-TYPE
			SYNTAX Integer32
			MAX-ACCESS read-only
			STATUS current
			DESCRIPTION
				"Satellite Vehicle Number - This is the identification number of the satellite."
			::= { gnss1CoordEntry 2 }


		-- 1.3.6.1.4.1.43913.16.4.1.16.1.3
		gnss1CoordSVType OBJECT-TYPE
			SYNTAX SVTYPE
			MAX-ACCESS read-only
			STATUS current
			DESCRIPTION
				"BD/GPS Satellite."
			::= { gnss1CoordEntry 3 }


		-- 1.3.6.1.4.1.43913.16.4.1.16.1.4
		gnss1CoordX OBJECT-TYPE
			SYNTAX DisplayString
			MAX-ACCESS read-only
			STATUS current
			DESCRIPTION
				"SAT coordinate X ."
			::= { gnss1CoordEntry 4 }


		-- 1.3.6.1.4.1.43913.16.4.1.16.1.5
		gnss1CoordY OBJECT-TYPE
			SYNTAX DisplayString
			MAX-ACCESS read-only
			STATUS current
			DESCRIPTION
				"SAT coordinate Y."
			::= { gnss1CoordEntry 5 }


		-- 1.3.6.1.4.1.43913.16.4.1.16.1.6
		gnss1CoordZ OBJECT-TYPE
			SYNTAX DisplayString
			MAX-ACCESS read-only
			STATUS current
			DESCRIPTION
				"SAT coordinate Z."
			::= { gnss1CoordEntry 6 }


		-- 1.3.6.1.4.1.43913.16.4.1.16.1.7
		gnss1ClkCorr OBJECT-TYPE
			SYNTAX DisplayString
			MAX-ACCESS read-only
			STATUS current
			DESCRIPTION
				"SAT clock correction."
			::= { gnss1CoordEntry 7 }


		-- 1.3.6.1.4.1.43913.16.4.1.17
		gnss1CVState OBJECT-TYPE
			SYNTAX ActionState
			MAX-ACCESS read-write
			STATUS current
			DESCRIPTION
				"Show / Set GNSS-1 common-view state: 0 - disable, 1 - enable."
			::= { gnss1 17 }

		-- 1.3.6.1.4.1.43913.1.4.1.20
		gnss1CVStationType OBJECT-TYPE
			SYNTAX CVStationType
			MAX-ACCESS read-write
			STATUS current
			DESCRIPTION
				"Show / Set GNSS-1 common-view station type: 0 - server, 1 - client, 2 - relay."
			::= { gnss1 20 }


		-- 1.3.6.1.4.1.43913.16.4.1.21
		gnss1CVStationID OBJECT-TYPE
			SYNTAX Integer32 (1..2147483647)
			MAX-ACCESS read-write
			STATUS current
			DESCRIPTION
				"Show / Set GNSS-1 common-view station ID."
			::= { gnss1 21 }


		-- 1.3.6.1.4.1.43913.16.4.1.23
		gnss1CVServerIP OBJECT-TYPE
			SYNTAX DisplayString
			MAX-ACCESS read-write
			STATUS current
			DESCRIPTION
				"Show / Set GNSS-1 common-view server IP for client station: xxx.xxx.xxx.xxx"
			::= { gnss1 23 }


		-- 1.3.6.1.4.1.43913.16.4.1.24
		gnss1CVCommPort OBJECT-TYPE
			SYNTAX Integer32
			MAX-ACCESS read-write
			STATUS current
			DESCRIPTION
				"Show / Set GNSS-1 common-view network communication port."
			::= { gnss1 24 }


		-- 1.3.6.1.4.1.43913.16.4.1.25
		gnss1CVIntDelay OBJECT-TYPE
			SYNTAX Integer32
			MAX-ACCESS read-write
			STATUS current
			DESCRIPTION
				"Show / Set GNSS-1 common-view GNSS receiver internal delay(ns)."
			::= { gnss1 25 }


		-- 1.3.6.1.4.1.43913.16.4.1.26
		gnss1CVCableDelay OBJECT-TYPE
			SYNTAX Integer32
			MAX-ACCESS read-write
			STATUS current
			DESCRIPTION
				"Show / Set GNSS-1 common-view GNSS receiver cable delay(ns)."
			::= { gnss1 26 }


		-- 1.3.6.1.4.1.43913.16.4.1.27
		gnss1CVRefDelay OBJECT-TYPE
			SYNTAX Integer32
			MAX-ACCESS read-write
			STATUS current
			DESCRIPTION
				"Show / Set GNSS-1 common-view GNSS receiver reference delay(ns)."
			::= { gnss1 27 }


		-- 1.3.6.1.4.1.43913.16.4.1.28
		gnss1CVOffset OBJECT-TYPE
			SYNTAX Integer32
			MAX-ACCESS read-only
			STATUS current
			DESCRIPTION
				"Show GNSS-1 common-view offset(ns) of local-remote."
			::= { gnss1 28 }


		-- 1.3.6.1.4.1.43913.16.4.1.29
		gnss1CVReqDur OBJECT-TYPE
			SYNTAX Integer32
			MAX-ACCESS read-write
			STATUS current
			DESCRIPTION
				"Show GNSS-1 common-view request duration."
			::= { gnss1 29 }


		-- 1.3.6.1.4.1.43913.16.4.1.30
		gnss1CVReqIntv OBJECT-TYPE
			SYNTAX Integer32
			MAX-ACCESS read-write
			STATUS current
			DESCRIPTION
				"Show GNSS-1 common-view request interval. It should be 1,60,300,600,960"
			::= { gnss1 30 }

		-- 1.3.6.1.4.1.43913.16.4.1.31
        gnss1CVProfileServer OBJECT-TYPE
			SYNTAX CVProfileType
			MAX-ACCESS read-write
			STATUS current
			DESCRIPTION
				"Show GNSS-1 common-view profile. 0--CMCC, 1--SGCC"
			::= { gnss1 31 }

        -- 1.3.6.1.4.1.43913.16.4.1.37
        gnss1CVProfileClient OBJECT-TYPE
            SYNTAX CVProfileTypeClient
            MAX-ACCESS read-write
            STATUS current
            DESCRIPTION
                "Show GNSS-1 common-view profile client. 0--CMCC, 1--SGCC,2--NTSC"
            ::= { gnss1 37 }

		-- 1.3.6.1.4.1.43913.16.4.2
		gnss2 OBJECT IDENTIFIER ::= { gnss 2 }


		-- 1.3.6.1.4.1.43913.16.4.2.1
		gnss2State OBJECT-TYPE
			SYNTAX ActionState
			MAX-ACCESS read-write
			STATUS current
			DESCRIPTION
				"Show / Set GNSS-2 state, disable(0), enable(1)."
			::= { gnss2 1 }


		-- 1.3.6.1.4.1.43913.16.4.2.2
		gnss2Mode OBJECT-TYPE
			SYNTAX GPSMode
			MAX-ACCESS read-write
			STATUS current
			DESCRIPTION
				"GNSS-2 operation mode. It is defined as follows: auto(0), manual(1).
				When the auto mode is selected, manually setting gnss position is prohibited.
				"
			::= { gnss2 2 }


		-- 1.3.6.1.4.1.43913.16.4.2.3
		gnss2Mask OBJECT-TYPE
			SYNTAX Integer32
			MAX-ACCESS read-write
			STATUS current
			DESCRIPTION
				"Show / Set GNSS-2 mask."
			::= { gnss2 3 }


		-- 1.3.6.1.4.1.43913.16.4.2.4
		gnss2TrackMode OBJECT-TYPE
			SYNTAX TrackMode
			MAX-ACCESS read-write
			STATUS current
			DESCRIPTION
				"Show / Set GNSS-2 track mode."
			::= { gnss2 4 }


		-- 1.3.6.1.4.1.43913.16.4.2.5
		gnss2CableDelay OBJECT-TYPE
			SYNTAX Integer32
			MAX-ACCESS read-write
			STATUS current
			DESCRIPTION
				"Show / Set GNSS-2 cable delay."
			::= { gnss2 5 }


		-- 1.3.6.1.4.1.43913.16.4.2.6
		gnss2Priority OBJECT-TYPE
			SYNTAX Integer32
			MAX-ACCESS read-write
			STATUS current
			DESCRIPTION
				"Show / Set GNSS-2 priority."
			::= { gnss2 6 }


		-- 1.3.6.1.4.1.43913.16.4.2.7
		gnss2PQLState OBJECT-TYPE
			SYNTAX ActionState
			MAX-ACCESS read-write
			STATUS current
			DESCRIPTION
				"Show / Set GNSS-2 PQL state, disable(0), enable(1)."
			::= { gnss2 7 }


		-- 1.3.6.1.4.1.43913.16.4.2.8
		gnss2PQL OBJECT-TYPE
			SYNTAX Integer32
			MAX-ACCESS read-write
			STATUS current
			DESCRIPTION
				"Show / Set GNSS-2 PQL value."
			::= { gnss2 8 }


		-- 1.3.6.1.4.1.43913.16.4.2.9
		gnss2CurrentPosMode OBJECT-TYPE
			SYNTAX GPSPosMode
			MAX-ACCESS read-only
			STATUS current
			DESCRIPTION
				"Show GNSS-2 current position mode, survey(0), hold(1), manual(2)."
			::= { gnss2 9 }


		-- 1.3.6.1.4.1.43913.16.4.2.10
		gnss2CurrentPosition OBJECT-TYPE
			SYNTAX DisplayString
			MAX-ACCESS read-only
			STATUS current
			DESCRIPTION
				"Show GNSS-2 current position. The format is latitude,longitude,hight."
			::= { gnss2 10 }


		-- 1.3.6.1.4.1.43913.16.4.2.11
		gnss2PositionConfig OBJECT-TYPE
			SYNTAX DisplayString
			MAX-ACCESS read-write
			STATUS current
			DESCRIPTION
				"The configuration of GNSS-2 position. The format is latitude,longitude,hight. Before the GNSS-2 position is configured,
				GNSS-2 mode should be setup as manual mode."
			::= { gnss2 11 }


		-- 1.3.6.1.4.1.43913.16.4.2.12
		gnss2SVTable OBJECT-TYPE
			SYNTAX SEQUENCE OF Gnss2SVEntry
			MAX-ACCESS not-accessible
			STATUS current
			DESCRIPTION
				"The tracked satellites table which provides the information about the satellites being tracked."
			::= { gnss2 12 }


		-- 1.3.6.1.4.1.43913.16.4.2.12.1
		gnss2SVEntry OBJECT-TYPE
			SYNTAX Gnss2SVEntry
			MAX-ACCESS not-accessible
			STATUS current
			DESCRIPTION
				"The entry of the satellites being tracked."
			INDEX { gnss2Index }
			::= { gnss2SVTable 1 }


		Gnss2SVEntry ::=
			SEQUENCE {
				gnss2Index
					Integer32,
				gnss2SVNum
					Integer32,
				gnss2SNR
					Integer32,
				gnss2Health
					GPSHealthy,
				gnss2Azimuth
					Integer32,
				gnss2Elevation
					Integer32,
                gnss2Signal
                    DisplayString,
                gnss2SatUsed
                    DisplayString
			 }

		-- 1.3.6.1.4.1.43913.16.4.2.12.1.1
		gnss2Index OBJECT-TYPE
			SYNTAX Integer32 (1..60)
			MAX-ACCESS not-accessible
			STATUS current
			DESCRIPTION
				"The index of tracked satellites table."
			::= { gnss2SVEntry 1 }


		-- 1.3.6.1.4.1.43913.16.4.2.12.1.2
		gnss2SVNum OBJECT-TYPE
			SYNTAX Integer32
			MAX-ACCESS read-only
			STATUS current
			DESCRIPTION
				"Satellite Vehicle Number - This is the identification number of the satellite being tracked."
			::= { gnss2SVEntry 2 }


		-- 1.3.6.1.4.1.43913.16.4.2.12.1.3
		gnss2SNR OBJECT-TYPE
			SYNTAX Integer32
			MAX-ACCESS read-only
			STATUS current
			DESCRIPTION
				"Signal to Noise Ratio."
			::= { gnss2SVEntry 3 }


		-- 1.3.6.1.4.1.43913.16.4.2.12.1.4
		gnss2Health OBJECT-TYPE
			SYNTAX GPSHealthy
			MAX-ACCESS read-only
			STATUS current
			DESCRIPTION
				"Indicates the health of the satellite. States are as follows: healthy(1), unhealthy(2)."
			::= { gnss2SVEntry 4 }


		-- 1.3.6.1.4.1.43913.16.4.2.12.1.5
		gnss2Azimuth OBJECT-TYPE
			SYNTAX Integer32
			MAX-ACCESS read-only
			STATUS current
			DESCRIPTION
				"Satellites horizontal position measured in degrees clockwise from the north."
			::= { gnss2SVEntry 5 }


		-- 1.3.6.1.4.1.43913.16.4.2.12.1.6
		gnss2Elevation OBJECT-TYPE
			SYNTAX Integer32
			MAX-ACCESS read-only
			STATUS current
			DESCRIPTION
				"Vertical position of satellite in degrees from the horizon."
			::= { gnss2SVEntry 6 }


		-- 1.3.6.1.4.1.43913.16.4.2.12.1.7
		gnss2Signal OBJECT-TYPE
			SYNTAX DisplayString
			MAX-ACCESS read-only
			STATUS current
			DESCRIPTION
				"SAT signal. Unknown,L1CA,L2CL,L2CM,B1D1,B1D2,B2D1,B2D2"
			::= { gnss2SVEntry 7 }


		-- 1.3.6.1.4.1.43913.16.4.2.12.1.8
		gnss2SatUsed OBJECT-TYPE
			SYNTAX DisplayString
			MAX-ACCESS read-only
			STATUS current
			DESCRIPTION
				"SAT used flag. Yes or No"
			::= { gnss2SVEntry 8}


		-- 1.3.6.1.4.1.43913.16.4.2.13
		gnss2InfoTable OBJECT-TYPE
			SYNTAX SEQUENCE OF Gnss2InfoEntry
			MAX-ACCESS not-accessible
			STATUS current
			DESCRIPTION
				"The GNSS-2 engine infomation table."
			::= { gnss2 13 }


		-- 1.3.6.1.4.1.43913.16.4.2.13.1
		gnss2InfoEntry OBJECT-TYPE
			SYNTAX Gnss2InfoEntry
			MAX-ACCESS not-accessible
			STATUS current
			DESCRIPTION
				"The entry of GNSS-2 engine infomation table."
			INDEX { gnss2InfoIndex }
			::= { gnss2InfoTable 1 }


		Gnss2InfoEntry ::=
			SEQUENCE {
				gnss2InfoIndex
					Integer32,
				gnss2InfoVendor
					DisplayString,
				gnss2InfoName
					DisplayString,
				gnss2InfoSWVer
					DisplayString,
				gnss2InfoHWVer
					DisplayString
			 }

		-- 1.3.6.1.4.1.43913.16.4.2.13.1.1
		gnss2InfoIndex OBJECT-TYPE
			SYNTAX Integer32 (1)
			MAX-ACCESS not-accessible
			STATUS current
			DESCRIPTION
				"The index of GNSS-2 engine infomation table."
			::= { gnss2InfoEntry 1 }


		-- 1.3.6.1.4.1.43913.16.4.2.13.1.2
		gnss2InfoVendor OBJECT-TYPE
			SYNTAX DisplayString
			MAX-ACCESS read-only
			STATUS current
			DESCRIPTION
				"The vendor of GNSS-2 engine."
			::= { gnss2InfoEntry 2 }


		-- 1.3.6.1.4.1.43913.16.4.2.13.1.3
		gnss2InfoName OBJECT-TYPE
			SYNTAX DisplayString
			MAX-ACCESS read-only
			STATUS current
			DESCRIPTION
				"The product name of GNSS-2 engine."
			::= { gnss2InfoEntry 3 }


		-- 1.3.6.1.4.1.43913.16.4.2.13.1.4
		gnss2InfoSWVer OBJECT-TYPE
			SYNTAX DisplayString
			MAX-ACCESS read-only
			STATUS current
			DESCRIPTION
				"The software version of GNSS-2 engine."
			::= { gnss2InfoEntry 4 }


		-- 1.3.6.1.4.1.43913.16.4.2.13.1.5
		gnss2InfoHWVer OBJECT-TYPE
			SYNTAX DisplayString
			MAX-ACCESS read-only
			STATUS current
			DESCRIPTION
				"The hardware version of GNSS-2 engine."
			::= { gnss2InfoEntry 5 }


		-- 1.3.6.1.4.1.43913.16.4.2.14
		gnss2ClockStatuc OBJECT-TYPE
			SYNTAX DisplayString
			MAX-ACCESS read-only
			STATUS current
			DESCRIPTION
				"Show GNSS-2 clock status. "
			::= { gnss2 14 }


		-- 1.3.6.1.4.1.43913.16.4.2.15
		gnss2AeroCorrTable OBJECT-TYPE
			SYNTAX SEQUENCE OF Gnss2AeroCorrEntry
			MAX-ACCESS not-accessible
			STATUS current
			DESCRIPTION
				"The table which provides the information about the satellites aero-correction."
			::= { gnss2 15 }


		-- 1.3.6.1.4.1.43913.16.4.2.15.1
		gnss2AeroCorrEntry OBJECT-TYPE
			SYNTAX Gnss2AeroCorrEntry
			MAX-ACCESS not-accessible
			STATUS current
			DESCRIPTION
				"The entry of the satellites."
			INDEX { gnss2AeroCorrIndex }
			::= { gnss2AeroCorrTable 1 }


		Gnss2AeroCorrEntry ::=
			SEQUENCE {
				gnss2AeroCorrIndex
					Integer32,
				gnss2AeroCorrSVNum
					Integer32,
				gnss2AeroCorrSVType
					SVTYPE,
				gnss2AeroCorrIono
					DisplayString,
				gnss2AeroCorrTropo
					DisplayString
			 }

		-- 1.3.6.1.4.1.43913.16.4.2.15.1.1
		gnss2AeroCorrIndex OBJECT-TYPE
			SYNTAX Integer32 (1..60)
			MAX-ACCESS not-accessible
			STATUS current
			DESCRIPTION
				"The index of tracked satellites table. GPS: 1-30, BD: 31-60"
			::= { gnss2AeroCorrEntry 1 }


		-- 1.3.6.1.4.1.43913.16.4.2.15.1.2
		gnss2AeroCorrSVNum OBJECT-TYPE
			SYNTAX Integer32
			MAX-ACCESS read-only
			STATUS current
			DESCRIPTION
				"Satellite Vehicle Number - This is the identification number of the satellite."
			::= { gnss2AeroCorrEntry 2 }


		-- 1.3.6.1.4.1.43913.16.4.2.15.1.3
		gnss2AeroCorrSVType OBJECT-TYPE
			SYNTAX SVTYPE
			MAX-ACCESS read-only
			STATUS current
			DESCRIPTION
				"BD/GPS Satellite."
			::= { gnss2AeroCorrEntry 3 }


		-- 1.3.6.1.4.1.43913.16.4.2.15.1.4
		gnss2AeroCorrIono OBJECT-TYPE
			SYNTAX DisplayString
			MAX-ACCESS read-only
			STATUS current
			DESCRIPTION
				"SAT iono correction."
			::= { gnss2AeroCorrEntry 4 }


		-- 1.3.6.1.4.1.43913.16.4.2.15.1.5
		gnss2AeroCorrTropo OBJECT-TYPE
			SYNTAX DisplayString
			MAX-ACCESS read-only
			STATUS current
			DESCRIPTION
				"SAT tropo correction."
			::= { gnss2AeroCorrEntry 5 }


		-- 1.3.6.1.4.1.43913.16.4.2.16
		gnss2CoordTable OBJECT-TYPE
			SYNTAX SEQUENCE OF Gnss2CoordEntry
			MAX-ACCESS not-accessible
			STATUS current
			DESCRIPTION
				"The table which provides the information about the satellites coordinate."
			::= { gnss2 16 }


		-- 1.3.6.1.4.1.43913.16.4.2.16.1
		gnss2CoordEntry OBJECT-TYPE
			SYNTAX Gnss2CoordEntry
			MAX-ACCESS not-accessible
			STATUS current
			DESCRIPTION
				"The entry of the satellites."
			INDEX { gnss2CoordIndex }
			::= { gnss2CoordTable 1 }


		Gnss2CoordEntry ::=
			SEQUENCE {
				gnss2CoordIndex
					Integer32,
				gnss2CoordSVNum
					Integer32,
				gnss2CoordSVType
					SVTYPE,
				gnss2CoordX
					DisplayString,
				gnss2CoordY
					DisplayString,
				gnss2CoordZ
					DisplayString,
				gnss2ClkCorr
					DisplayString
			 }

		-- 1.3.6.1.4.1.43913.16.4.2.16.1.1
		gnss2CoordIndex OBJECT-TYPE
			SYNTAX Integer32 (1..60)
			MAX-ACCESS not-accessible
			STATUS current
			DESCRIPTION
				"The index of tracked satellites table. GPS: 1-30, BD: 31-60"
			::= { gnss2CoordEntry 1 }


		-- 1.3.6.1.4.1.43913.16.4.2.16.1.2
		gnss2CoordSVNum OBJECT-TYPE
			SYNTAX Integer32
			MAX-ACCESS read-only
			STATUS current
			DESCRIPTION
				"Satellite Vehicle Number - This is the identification number of the satellite."
			::= { gnss2CoordEntry 2 }


		-- 1.3.6.1.4.1.43913.16.4.2.16.1.3
		gnss2CoordSVType OBJECT-TYPE
			SYNTAX SVTYPE
			MAX-ACCESS read-only
			STATUS current
			DESCRIPTION
				"BD/GPS Satellite."
			::= { gnss2CoordEntry 3 }


		-- 1.3.6.1.4.1.43913.16.4.2.16.1.4
		gnss2CoordX OBJECT-TYPE
			SYNTAX DisplayString
			MAX-ACCESS read-only
			STATUS current
			DESCRIPTION
				"SAT coordinate X ."
			::= { gnss2CoordEntry 4 }


		-- 1.3.6.1.4.1.43913.16.4.2.16.1.5
		gnss2CoordY OBJECT-TYPE
			SYNTAX DisplayString
			MAX-ACCESS read-only
			STATUS current
			DESCRIPTION
				"SAT coordinate Y."
			::= { gnss2CoordEntry 5 }


		-- 1.3.6.1.4.1.43913.16.4.2.16.1.6
		gnss2CoordZ OBJECT-TYPE
			SYNTAX DisplayString
			MAX-ACCESS read-only
			STATUS current
			DESCRIPTION
				"SAT coordinate Z."
			::= { gnss2CoordEntry 6 }


		-- 1.3.6.1.4.1.43913.16.4.2.16.1.7
		gnss2ClkCorr OBJECT-TYPE
			SYNTAX DisplayString
			MAX-ACCESS read-only
			STATUS current
			DESCRIPTION
				"SAT clock correction."
			::= { gnss2CoordEntry 7 }


		-- 1.3.6.1.4.1.43913.16.4.2.17
		gnss2CVState OBJECT-TYPE
			SYNTAX ActionState
			MAX-ACCESS read-write
			STATUS current
			DESCRIPTION
				"Show / Set GNSS-2 common-view state: 0 - disable, 1 - enable."
			::= { gnss2 17 }

		-- 1.3.6.1.4.1.43913.16.4.2.20
		gnss2CVStationType OBJECT-TYPE
			SYNTAX CVStationType
			MAX-ACCESS read-write
			STATUS current
			DESCRIPTION
				"Show / Set GNSS-2 common-view station type: 0 - server, 1 - client, 2 - relay."
			::= { gnss2 20 }


		-- 1.3.6.1.4.1.43913.16.4.2.21
		gnss2CVStationID OBJECT-TYPE
			SYNTAX Integer32 (1..2147483647)
			MAX-ACCESS read-write
			STATUS current
			DESCRIPTION
				"Show / Set GNSS-2 common-view station ID."
			::= { gnss2 21 }


		-- 1.3.6.1.4.1.43913.16.4.2.23
		gnss2CVServerIP OBJECT-TYPE
			SYNTAX DisplayString
			MAX-ACCESS read-write
			STATUS current
			DESCRIPTION
				"Show / Set GNSS-2 common-view server IP for client station: xxx.xxx.xxx.xxx"
			::= { gnss2 23 }


		-- 1.3.6.1.4.1.43913.16.4.2.24
		gnss2CVCommPort OBJECT-TYPE
			SYNTAX Integer32
			MAX-ACCESS read-write
			STATUS current
			DESCRIPTION
				"Show / Set GNSS-2 common-view network communication port."
			::= { gnss2 24 }


		-- 1.3.6.1.4.1.43913.16.4.2.25
		gnss2CVIntDelay OBJECT-TYPE
			SYNTAX Integer32
			MAX-ACCESS read-write
			STATUS current
			DESCRIPTION
				"Show / Set GNSS-2 common-view GNSS receiver internal delay(ns)."
			::= { gnss2 25 }


		-- 1.3.6.1.4.1.43913.16.4.2.26
		gnss2CVCableDelay OBJECT-TYPE
			SYNTAX Integer32
			MAX-ACCESS read-write
			STATUS current
			DESCRIPTION
				"Show / Set GNSS-2 common-view GNSS receiver cable delay(ns)."
			::= { gnss2 26 }


		-- 1.3.6.1.4.1.43913.16.4.2.27
		gnss2CVRefDelay OBJECT-TYPE
			SYNTAX Integer32
			MAX-ACCESS read-write
			STATUS current
			DESCRIPTION
				"Show / Set GNSS-2 common-view GNSS receiver reference delay(ns)."
			::= { gnss2 27 }


		-- 1.3.6.1.4.1.43913.16.4.2.28
		gnss2CVOffset OBJECT-TYPE
			SYNTAX Integer32
			MAX-ACCESS read-only
			STATUS current
			DESCRIPTION
				"Show GNSS-2 common-view offset(ns) of local-remote."
			::= { gnss2 28 }


		-- 1.3.6.1.4.1.43913.16.4.2.29
		gnss2CVReqDur OBJECT-TYPE
			SYNTAX Integer32
			MAX-ACCESS read-write
			STATUS current
			DESCRIPTION
				"Show / Set GNSS-2 common-view request duration."
			::= { gnss2 29 }


		-- 1.3.6.1.4.1.43913.16.4.2.30
		gnss2CVReqIntv OBJECT-TYPE
			SYNTAX Integer32
			MAX-ACCESS read-write
			STATUS current
			DESCRIPTION
				"Show / Set GNSS-2 common-view request interval. It should be 1,60,300,600,960"
			::= { gnss2 30 }

		-- 1.3.6.1.4.1.43913.16.4.2.31
		gnss2CVProfileServer OBJECT-TYPE
			SYNTAX CVProfileType
			MAX-ACCESS read-write
			STATUS current
			DESCRIPTION
				"Show GNSS-2 common-view profile. 0--CMCC, 1--SGCC"
			::= { gnss2 31 }

        -- 1.3.6.1.4.1.43913.16.4.2.37
        gnss2CVProfileClient OBJECT-TYPE
            SYNTAX CVProfileTypeClient
            MAX-ACCESS read-write
            STATUS current
            DESCRIPTION
                "Show GNSS-2 common-view profile client. 0--CMCC, 1--SGCC,2--NTSC"
            ::= { gnss2 37 }

		-- 1.3.6.1.4.1.43913.16.4.3
		gnssCfgNotifyElements OBJECT IDENTIFIER ::= { gnss 3 }


		-- 1.3.6.1.4.1.43913.16.4.3.1
		notifyGNSSIndex OBJECT-TYPE
			SYNTAX Integer32 (1..2)
			MAX-ACCESS read-only
			STATUS current
			DESCRIPTION
				"Notification GNSS index."
			::= { gnssCfgNotifyElements 1 }


		-- 1.3.6.1.4.1.43913.16.4.3.2
		notifyGNSSState OBJECT-TYPE
			SYNTAX ActionState
			MAX-ACCESS read-only
			STATUS current
			DESCRIPTION
				"Notification GNSS state."
			::= { gnssCfgNotifyElements 2 }


		-- 1.3.6.1.4.1.43913.16.4.3.3
		notifyGNSSMode OBJECT-TYPE
			SYNTAX GPSMode
			MAX-ACCESS read-only
			STATUS current
			DESCRIPTION
				"Notification GNSS mode."
			::= { gnssCfgNotifyElements 3 }


		-- 1.3.6.1.4.1.43913.16.4.3.4
		notifyGNSSMask OBJECT-TYPE
			SYNTAX Integer32
			MAX-ACCESS read-only
			STATUS current
			DESCRIPTION
				"Notification GNSS mask."
			::= { gnssCfgNotifyElements 4 }


		-- 1.3.6.1.4.1.43913.16.4.3.5
		notifyGNSSTrackMode OBJECT-TYPE
			SYNTAX TrackMode
			MAX-ACCESS read-only
			STATUS current
			DESCRIPTION
				"Notification GNSS track mode."
			::= { gnssCfgNotifyElements 5 }


		-- 1.3.6.1.4.1.43913.16.4.3.6
		notifyGNSSCableDelay OBJECT-TYPE
			SYNTAX Unsigned32
			MAX-ACCESS read-only
			STATUS current
			DESCRIPTION
				"Notification GNSS cable delay."
			::= { gnssCfgNotifyElements 6 }


		-- 1.3.6.1.4.1.43913.16.4.3.7
		notifyGNSSPriority OBJECT-TYPE
			SYNTAX Integer32
			MAX-ACCESS read-only
			STATUS current
			DESCRIPTION
				"Notification GNSS priority."
			::= { gnssCfgNotifyElements 7 }


		-- 1.3.6.1.4.1.43913.16.4.3.8
		notifyGNSSPQLState OBJECT-TYPE
			SYNTAX ActionState
			MAX-ACCESS read-only
			STATUS current
			DESCRIPTION
				"Notification GNSS PQL state."
			::= { gnssCfgNotifyElements 8 }


		-- 1.3.6.1.4.1.43913.16.4.3.9
		notifyGNSSPQL OBJECT-TYPE
			SYNTAX Integer32
			MAX-ACCESS read-only
			STATUS current
			DESCRIPTION
				"Notification GNSS PQL."
			::= { gnssCfgNotifyElements 9 }


		-- 1.3.6.1.4.1.43913.16.4.3.10
		notifyGNSSPosCfg OBJECT-TYPE
			SYNTAX DisplayString
			MAX-ACCESS read-only
			STATUS current
			DESCRIPTION
				"Notification GNSS position configuration."
			::= { gnssCfgNotifyElements 10 }


		-- 1.3.6.1.4.1.43913.16.4.4
		sm2000TrapGNSSCfg NOTIFICATION-TYPE
			OBJECTS { notifyGNSSIndex, notifyGNSSState, notifyGNSSMode, notifyGNSSMask, notifyGNSSTrackMode, notifyGNSSCableDelay, notifyGNSSPriority, notifyGNSSPQLState, notifyGNSSPQL, notifyGNSSPosCfg }
			STATUS current
			DESCRIPTION
				"SM2000-5G GNSS configuration trap object which specifies GNSS ID, state, mode, mask, track mode, cable delay, priority, PQL state, PQL and position configuration."
			::= { gnss 4 }

		-- 1.3.6.1.4.1.43913.16.6
		ppsTOD OBJECT IDENTIFIER ::= { sm2000-5g 6 }


		-- 1.3.6.1.4.1.43913.16.6.1
		ppsTODTable OBJECT-TYPE
			SYNTAX SEQUENCE OF PpsTODEntry
			MAX-ACCESS not-accessible
			STATUS current
			DESCRIPTION
				"PPS-TOD configuration table."
			::= { ppsTOD 1 }


		-- 1.3.6.1.4.1.43913.16.6.1.1
		ppsTODEntry OBJECT-TYPE
			SYNTAX PpsTODEntry
			MAX-ACCESS not-accessible
			STATUS current
			DESCRIPTION
				"The entry of PPS-TOD configuration table."
			INDEX { ppsTODIndex }
			::= { ppsTODTable 1 }


		PpsTODEntry ::=
			SEQUENCE {
				ppsTODIndex
					Integer32,
				ppsTODPortID
					Integer32,
				ppsTODState
					ActionState,
				ppsTODPriority
					Integer32,
				ppsTODCableDelay
					Unsigned32,
				ppsTODPQLState
					ActionState,
				ppsTODPQL
					Integer32
			 }

		-- 1.3.6.1.4.1.43913.16.6.1.1.1
		ppsTODIndex OBJECT-TYPE
			SYNTAX Integer32 (1..2)
			MAX-ACCESS not-accessible
			STATUS current
			DESCRIPTION
				"The index of PPS-TOD configuration table."
			::= { ppsTODEntry 1 }


		-- 1.3.6.1.4.1.43913.16.6.1.1.2
		ppsTODPortID OBJECT-TYPE
			SYNTAX Integer32
			MAX-ACCESS read-only
			STATUS current
			DESCRIPTION
				"It should be port-1(1) or port-2(2)"
			::= { ppsTODEntry 2 }


		-- 1.3.6.1.4.1.43913.16.6.1.1.3
		ppsTODState OBJECT-TYPE
			SYNTAX ActionState
			MAX-ACCESS read-write
			STATUS current
			DESCRIPTION
				"Show / Set pps-tod port state, disable(0) or enable(1)."
			::= { ppsTODEntry 3 }


		-- 1.3.6.1.4.1.43913.16.6.1.1.4
		ppsTODPriority OBJECT-TYPE
			SYNTAX Integer32 (0..20)
			MAX-ACCESS read-write
			STATUS current
			DESCRIPTION
				"Show / Set pps-tod port priority."
			::= { ppsTODEntry 4 }


		-- 1.3.6.1.4.1.43913.16.6.1.1.5
		ppsTODCableDelay OBJECT-TYPE
			SYNTAX Unsigned32
			MAX-ACCESS read-write
			STATUS current
			DESCRIPTION
				"Show / Set pps-tod port cable delay."
			::= { ppsTODEntry 5 }


		-- 1.3.6.1.4.1.43913.16.6.1.1.6
		ppsTODPQLState OBJECT-TYPE
			SYNTAX ActionState
			MAX-ACCESS read-write
			STATUS current
			DESCRIPTION
				"Show / Set pps-tod PQL state, disable(0) or enable(1)."
			::= { ppsTODEntry 6 }


		-- 1.3.6.1.4.1.43913.16.6.1.1.7
		ppsTODPQL OBJECT-TYPE
			SYNTAX Integer32
			MAX-ACCESS read-write
			STATUS current
			DESCRIPTION
				"Show / Set pps-tod PQL value."
			::= { ppsTODEntry 7 }


		-- 1.3.6.1.4.1.43913.16.6.2
		ppsTODStatusTable OBJECT-TYPE
			SYNTAX SEQUENCE OF PpsTODStatusEntry
			MAX-ACCESS not-accessible
			STATUS current
			DESCRIPTION
				"PPS-TOD status table."
			::= { ppsTOD 2 }


		-- 1.3.6.1.4.1.43913.16.6.2.1
		ppsTODStatusEntry OBJECT-TYPE
			SYNTAX PpsTODStatusEntry
			MAX-ACCESS not-accessible
			STATUS current
			DESCRIPTION
				"The entry of PPS-TOD status table."
			INDEX { ppsTODStatusIndex }
			::= { ppsTODStatusTable 1 }


		PpsTODStatusEntry ::=
			SEQUENCE {
				ppsTODStatusIndex
					Integer32,
				portID
					Integer32,
				portStatus
					PpsTODPortStatus,
				ppsStatus
					DisplayString,
				ppsPhaseOffset
					DisplayString,
				clockSource
					DisplayString,
				clockSourceStatus
					DisplayString,
				accuracy
					DisplayString,
				ppsTODAlarm
					DisplayString
			 }

		-- 1.3.6.1.4.1.43913.16.6.2.1.1
		ppsTODStatusIndex OBJECT-TYPE
			SYNTAX Integer32 (1..2)
			MAX-ACCESS not-accessible
			STATUS current
			DESCRIPTION
				"The index of PPS-TOD status table."
			::= { ppsTODStatusEntry 1 }


		-- 1.3.6.1.4.1.43913.16.6.2.1.2
		portID OBJECT-TYPE
			SYNTAX Integer32
			MAX-ACCESS read-only
			STATUS current
			DESCRIPTION
				"It should be port-1(1) or port-2(2)."
			::= { ppsTODStatusEntry 2 }


		-- 1.3.6.1.4.1.43913.16.6.2.1.3
		portStatus OBJECT-TYPE
			SYNTAX PpsTODPortStatus
			MAX-ACCESS read-only
			STATUS current
			DESCRIPTION
				"It should be one of disabled(0), normal(1) and error(2)."
			::= { ppsTODStatusEntry 3 }


		-- 1.3.6.1.4.1.43913.16.6.2.1.4
		ppsStatus OBJECT-TYPE
			SYNTAX DisplayString
			MAX-ACCESS read-only
			STATUS current
			DESCRIPTION
				"PPS status."
			::= { ppsTODStatusEntry 4 }


		-- 1.3.6.1.4.1.43913.16.6.2.1.5
		ppsPhaseOffset OBJECT-TYPE
			SYNTAX DisplayString
			MAX-ACCESS read-only
			STATUS current
			DESCRIPTION
				"PPS phase offset."
			::= { ppsTODStatusEntry 5 }


		-- 1.3.6.1.4.1.43913.16.6.2.1.6
		clockSource OBJECT-TYPE
			SYNTAX DisplayString
			MAX-ACCESS read-only
			STATUS current
			DESCRIPTION
				"PPS clock source."
			::= { ppsTODStatusEntry 6 }


		-- 1.3.6.1.4.1.43913.16.6.2.1.7
		clockSourceStatus OBJECT-TYPE
			SYNTAX DisplayString
			MAX-ACCESS read-only
			STATUS current
			DESCRIPTION
				"PPS clock source status."
			::= { ppsTODStatusEntry 7 }


		-- 1.3.6.1.4.1.43913.16.6.2.1.8
		accuracy OBJECT-TYPE
			SYNTAX DisplayString
			MAX-ACCESS read-only
			STATUS current
			DESCRIPTION
				"PPS accuracy."
			::= { ppsTODStatusEntry 8 }


		-- 1.3.6.1.4.1.43913.16.6.2.1.9
		ppsTODAlarm OBJECT-TYPE
			SYNTAX DisplayString
			MAX-ACCESS read-only
			STATUS current
			DESCRIPTION
				"PPS TOD alarm."
			::= { ppsTODStatusEntry 9 }





		-- 1.3.6.1.4.1.43913.16.13
		irig OBJECT IDENTIFIER ::= { sm2000-5g 14 }


		-- 1.3.6.1.4.1.43913.16.7.1
		irigTable OBJECT-TYPE
			SYNTAX SEQUENCE OF IrigEntry
			MAX-ACCESS not-accessible
			STATUS current
			DESCRIPTION
				"IRIG configuration table."
			::= { irig 1 }


		-- 1.3.6.1.4.1.43913.16.7.1.1
		irigEntry OBJECT-TYPE
			SYNTAX IrigEntry
			MAX-ACCESS not-accessible
			STATUS current
			DESCRIPTION
				"The entry of IRIG configuration table."
			INDEX { irigIndex }
			::= { irigTable 1 }


		IrigEntry ::=
			SEQUENCE {
				irigIndex
					Integer32,
				irigPortID
					Integer32,
				irigState
					ActionState,
				irigPriority
					Integer32,
				irigCableDelay
					Integer32,
				irigPQLState
					ActionState,
				irigPQL
					Integer32
			 }

		-- 1.3.6.1.4.1.43913.16.7.1.1.1
		irigIndex OBJECT-TYPE
			SYNTAX Integer32 (1..2)
			MAX-ACCESS not-accessible
			STATUS current
			DESCRIPTION
				"The index of irig configuration table."
			::= { irigEntry 1 }


		-- 1.3.6.1.4.1.43913.16.7.1.1.2
		irigPortID OBJECT-TYPE
			SYNTAX Integer32
			MAX-ACCESS read-only
			STATUS current
			DESCRIPTION
				"It should be port-1(1) or port-2(2)"
			::= { irigEntry 2 }


		-- 1.3.6.1.4.1.43913.16.7.1.1.3
		irigState OBJECT-TYPE
			SYNTAX ActionState
			MAX-ACCESS read-write
			STATUS current
			DESCRIPTION
				"Show / Set irig port state, disable(0) or enable(1)."
			::= { irigEntry 3 }


		-- 1.3.6.1.4.1.43913.16.7.1.1.4
		irigPriority OBJECT-TYPE
			SYNTAX Integer32 (0..20)
			MAX-ACCESS read-write
			STATUS current
			DESCRIPTION
				"Show / Set irig port priority."
			::= { irigEntry 4 }


		-- 1.3.6.1.4.1.43913.16.7.1.1.5
		irigCableDelay OBJECT-TYPE
			SYNTAX Integer32
			MAX-ACCESS read-only
			STATUS current
			DESCRIPTION
				"Show irig port cable delay. -500000000~500000000"
			::= { irigEntry 5 }


		-- 1.3.6.1.4.1.43913.16.7.1.1.6
		irigPQLState OBJECT-TYPE
			SYNTAX ActionState
			MAX-ACCESS read-write
			STATUS current
			DESCRIPTION
				"Show / Set irig PQL state, disable(0) or enable(1)."
			::= { irigEntry 6 }


		-- 1.3.6.1.4.1.43913.16.7.1.1.7
		irigPQL OBJECT-TYPE
			SYNTAX Integer32
			MAX-ACCESS read-write
			STATUS current
			DESCRIPTION
				"Show / Set irig PQL value."
			::= { irigEntry 7 }


		-- 1.3.6.1.4.1.43913.16.7.2
		irigStatusTable OBJECT-TYPE
			SYNTAX SEQUENCE OF IrigStatusEntry
			MAX-ACCESS not-accessible
			STATUS current
			DESCRIPTION
				"irig status table."
			::= { irig 2 }


		-- 1.3.6.1.4.1.43913.16.7.2.1
		irigStatusEntry OBJECT-TYPE
			SYNTAX IrigStatusEntry
			MAX-ACCESS not-accessible
			STATUS current
			DESCRIPTION
				"The entry of irig status table."
			INDEX { irigStatusIndex }
			::= { irigStatusTable 1 }


		IrigStatusEntry ::=
			SEQUENCE {
				irigStatusIndex
					Integer32,
				irigportID
					Integer32,
				irigportStatus
					PpsTODPortStatus,
				irigppsQuality
					DisplayString,
				irigppsPhaseOffset
					DisplayString
			 }

		-- 1.3.6.1.4.1.43913.16.7.2.1.1
		irigStatusIndex OBJECT-TYPE
			SYNTAX Integer32 (1..2)
			MAX-ACCESS not-accessible
			STATUS current
			DESCRIPTION
				"The index of irig status table."
			::= { irigStatusEntry 1 }


		-- 1.3.6.1.4.1.43913.16.7.2.1.2
		irigportID OBJECT-TYPE
			SYNTAX Integer32
			MAX-ACCESS read-only
			STATUS current
			DESCRIPTION
				"It should be port-1(1) or port-2(2)."
			::= { irigStatusEntry 2 }


		-- 1.3.6.1.4.1.43913.16.7.2.1.3
		irigportStatus OBJECT-TYPE
			SYNTAX PpsTODPortStatus
			MAX-ACCESS read-only
			STATUS current
			DESCRIPTION
				"It should be one of disabled(0), normal(1) and error(2)."
			::= { irigStatusEntry 3 }


		-- 1.3.6.1.4.1.43913.16.7.2.1.4
		irigppsQuality OBJECT-TYPE
			SYNTAX DisplayString
			MAX-ACCESS read-only
			STATUS current
			DESCRIPTION
				"IRIG-B quality level."
			::= { irigStatusEntry 4 }


		-- 1.3.6.1.4.1.43913.16.7.2.1.5
		irigppsPhaseOffset OBJECT-TYPE
			SYNTAX DisplayString
			MAX-ACCESS read-only
			STATUS current
			DESCRIPTION
				"PPS phase offset. In unit of ns."
			::= { irigStatusEntry 5 }


		-- 1.3.6.1.4.1.43913.16.6.3
		sm2000TrapPPSTod NOTIFICATION-TYPE
			OBJECTS { ppsTODPortID, ppsTODState, ppsTODPriority, ppsTODCableDelay, ppsTODPQLState, ppsTODPQL }
			STATUS current
			DESCRIPTION
				"SM2000-5G PPS-TOD input configuration trap object which specifies port ID, state, priority, cable delay, PQL state and PQL."
			::= { ppsTOD 3 }


		-- 1.3.6.1.4.1.43913.16.8
		inputOutput OBJECT IDENTIFIER ::= { sm2000-5g 8 }






		-- 1.3.6.1.4.1.43913.16.8.2
        outputOldE1Group OBJECT IDENTIFIER ::= { inputOutput 2 }

		-- 1.3.6.1.4.1.43913.16.8.2.1
		outputOldE1ConfigTable OBJECT-TYPE
			SYNTAX SEQUENCE OF OutputOldE1ConfigEntry
			MAX-ACCESS not-accessible
			STATUS current
			DESCRIPTION
				"old E1 card output configuration table."
			::= { outputOldE1Group 1 }


		-- 1.3.6.1.4.1.43913.16.8.2.1.1
		outputOldE1ConfigEntry OBJECT-TYPE
			SYNTAX OutputOldE1ConfigEntry
			MAX-ACCESS not-accessible
			STATUS current
			DESCRIPTION
				"The entry of E1 output configuration table."
			INDEX { outputE1Index, outputE1SlotIndex }
			::= { outputOldE1ConfigTable 1 }


		OutputOldE1ConfigEntry ::=
			SEQUENCE {
				outputE1Index
					Integer32,
				outputE1SlotIndex
					Integer32,
				outputE1State
					ActionState,
				outputE1FrameType
					OutputFrameType,
				outputE1CRCState
					ActionState,
				outputE1SSMState
					ActionState,
				outputE1SSMBit
					Integer32
			 }

		-- 1.3.6.1.4.1.43913.16.8.2.1.1.1
		outputE1Index OBJECT-TYPE
			SYNTAX Integer32 (1)
			MAX-ACCESS not-accessible
			STATUS current
			DESCRIPTION
				"The index of E1 output configuration table."
			::= { outputOldE1ConfigEntry 1 }

        -- 1.3.6.1.4.1.43913.16.8.2.1.1.2
		outputE1SlotIndex OBJECT-TYPE
			SYNTAX Integer32 (1..9)
			MAX-ACCESS not-accessible
			STATUS current
			DESCRIPTION
				"The slot index of E1 output configuration table."
			::= { outputOldE1ConfigEntry 2 }


		-- 1.3.6.1.4.1.43913.16.8.2.1.1.3
		outputE1State OBJECT-TYPE
			SYNTAX ActionState
			MAX-ACCESS read-write
			STATUS current
			DESCRIPTION
				"Show / Set E1 output state, disable(0) or enable(1)."
			::= { outputOldE1ConfigEntry 3 }


		-- 1.3.6.1.4.1.43913.16.8.2.1.1.4
		outputE1FrameType OBJECT-TYPE
			SYNTAX OutputFrameType
			MAX-ACCESS read-write
			STATUS current
			DESCRIPTION
				"Show / Set E1 output frame type, 2048KHZ(1) CCS(2), CAS(3)."
			::= { outputOldE1ConfigEntry 4 }


		-- 1.3.6.1.4.1.43913.16.8.2.1.1.5
		outputE1CRCState OBJECT-TYPE
			SYNTAX ActionState
			MAX-ACCESS read-write
			STATUS current
			DESCRIPTION
				"Show / Set E1 output CRC state, disable(0) or enable(1)."
			::= { outputOldE1ConfigEntry 5 }


		-- 1.3.6.1.4.1.43913.16.8.2.1.1.6
		outputE1SSMState OBJECT-TYPE
			SYNTAX ActionState
			MAX-ACCESS read-write
			STATUS current
			DESCRIPTION
				"Show / Set E1 output SSM state, disable(0) or enable(1)."
			::= { outputOldE1ConfigEntry 6 }


		-- 1.3.6.1.4.1.43913.16.8.2.1.1.7
		outputE1SSMBit OBJECT-TYPE
			SYNTAX Integer32
			MAX-ACCESS read-write
			STATUS current
			DESCRIPTION
				"Show / Set E1 output SSM bit."
			::= { outputOldE1ConfigEntry 7 }


		-- 1.3.6.1.4.1.43913.16.8.2.2
		outputOldE1GenerationTable OBJECT-TYPE
			SYNTAX SEQUENCE OF OutputOldE1GenerationEntry
			MAX-ACCESS not-accessible
			STATUS current
			DESCRIPTION
				"old old E1 card output configuration table."
			::= { outputOldE1Group 2 }


		-- 1.3.6.1.4.1.43913.16.8.2.2.1
		outputOldE1GenerationEntry OBJECT-TYPE
			SYNTAX OutputOldE1GenerationEntry
			MAX-ACCESS not-accessible
			STATUS current
			DESCRIPTION
				"The entry of old E1 output configuration table."
			INDEX { outputE1GenerationIndex }
			::= { outputOldE1GenerationTable 1 }


		OutputOldE1GenerationEntry ::=
			SEQUENCE {
				outputE1GenerationIndex
					Integer32,
				outputE1Warmup
					OutputControlE1,
				outputE1Freerun
					OutputControlE1,
				outputE1Holdover
					OutputControlE1,
				outputE1Fasttrack
					OutputControlE1
			 }

		-- 1.3.6.1.4.1.43913.16.8.2.2.1.1
		outputE1GenerationIndex	  OBJECT-TYPE
			SYNTAX Integer32 (1)
			MAX-ACCESS not-accessible
			STATUS current
			DESCRIPTION
				"The index of E1 output configuration table."
			::= { outputOldE1GenerationEntry 1 }

		-- 1.3.6.1.4.1.43913.16.8.2.2.1.2
		outputE1Warmup OBJECT-TYPE
			SYNTAX OutputControlE1
			MAX-ACCESS read-write
			STATUS current
			DESCRIPTION
				"Show / Set E1 output warm up, squelch(0), on(1), ais(2)."
			::= { outputOldE1GenerationEntry 2 }


		-- 1.3.6.1.4.1.43913.16.8.2.2.1.3
		outputE1Freerun OBJECT-TYPE
			SYNTAX OutputControlE1
			MAX-ACCESS read-write
			STATUS current
			DESCRIPTION
				"Show / Set E1 output free run, squelch(0), on(1), ais(2)."
			::= { outputOldE1GenerationEntry 3 }


		-- 1.3.6.1.4.1.43913.16.8.2.2.1.4
		outputE1Holdover OBJECT-TYPE
			SYNTAX OutputControlE1
			MAX-ACCESS read-write
			STATUS current
			DESCRIPTION
				"Show / Set E1 output hold over, squelch(0), on(1), ais(2)."
			::= { outputOldE1GenerationEntry 4 }


		-- 1.3.6.1.4.1.43913.16.8.2.2.1.5
		outputE1Fasttrack OBJECT-TYPE
			SYNTAX OutputControlE1
			MAX-ACCESS read-write
			STATUS current
			DESCRIPTION
				"Show / Set E1 output fast track, squelch(0), on(1), ais(2)."
			::= { outputOldE1GenerationEntry 5 }


		-- 1.3.6.1.4.1.43913.16.8.3
		output10MTable OBJECT-TYPE
			SYNTAX SEQUENCE OF Output10MEntry
			MAX-ACCESS not-accessible
			STATUS current
			DESCRIPTION
				"10M output configuration table."
			::= { inputOutput 3 }


		-- 1.3.6.1.4.1.43913.16.8.3.1
		output10MEntry OBJECT-TYPE
			SYNTAX Output10MEntry
			MAX-ACCESS not-accessible
			STATUS current
			DESCRIPTION
				"The entry of 10M output configuration table."
			INDEX { output10MIndex }
			::= { output10MTable 1 }


		Output10MEntry ::=
			SEQUENCE {
				output10MIndex
					Integer32,
				output10MState
					ActionState,
				output10MGenWarmup
					OutputControl,
				output10MGenFreerun
					OutputControl,
				output10MGenHoldover
					OutputControl,
				output10MGenFasttrack
					OutputControl
			 }

		-- 1.3.6.1.4.1.43913.16.8.3.1.1
		output10MIndex OBJECT-TYPE
			SYNTAX Integer32 (1)
			MAX-ACCESS not-accessible
			STATUS current
			DESCRIPTION
				"The index of 10M output configuration table."
			::= { output10MEntry 1 }


		-- 1.3.6.1.4.1.43913.16.8.3.1.2
		output10MState OBJECT-TYPE
			SYNTAX ActionState
			MAX-ACCESS read-write
			STATUS current
			DESCRIPTION
				"Show / Set 10M output state, disable(0), enable(1)."
			::= { output10MEntry 2 }


		-- 1.3.6.1.4.1.43913.16.8.3.1.3
		output10MGenWarmup OBJECT-TYPE
			SYNTAX OutputControl
			MAX-ACCESS read-write
			STATUS current
			DESCRIPTION
				"Show / Set 10M output generation warm up, squelch(0), on(1)."
			::= { output10MEntry 3 }


		-- 1.3.6.1.4.1.43913.16.8.3.1.4
		output10MGenFreerun OBJECT-TYPE
			SYNTAX OutputControl
			MAX-ACCESS read-write
			STATUS current
			DESCRIPTION
				"Show / Set 10M output generation free run, squelch(0), on(1)."
			::= { output10MEntry 4 }


		-- 1.3.6.1.4.1.43913.16.8.3.1.5
		output10MGenHoldover OBJECT-TYPE
			SYNTAX OutputControl
			MAX-ACCESS read-write
			STATUS current
			DESCRIPTION
				"Show / Set 10M output generation hold over, squelch(0), on(1)."
			::= { output10MEntry 5 }


		-- 1.3.6.1.4.1.43913.16.8.3.1.6
		output10MGenFasttrack OBJECT-TYPE
			SYNTAX OutputControl
			MAX-ACCESS read-write
			STATUS current
			DESCRIPTION
				"Show / Set 10M output generation fast track, squelch(0), on(1)."
			::= { output10MEntry 6 }


		-- 1.3.6.1.4.1.43913.16.8.4
		outputPPSTable OBJECT-TYPE
			SYNTAX SEQUENCE OF OutputPPSEntry
			MAX-ACCESS not-accessible
			STATUS current
			DESCRIPTION
				"PPS output configuration table."
			::= { inputOutput 4 }


		-- 1.3.6.1.4.1.43913.16.8.4.1
		outputPPSEntry OBJECT-TYPE
			SYNTAX OutputPPSEntry
			MAX-ACCESS not-accessible
			STATUS current
			DESCRIPTION
				"The entry of PPS output configuration table."
			INDEX { outputPPSIndex }
			::= { outputPPSTable 1 }


		OutputPPSEntry ::=
			SEQUENCE {
				outputPPSIndex
					Integer32,
				outputPPSState
					ActionState,
				outputPPSGenWarmup
					OutputControl,
				outputPPSGenFreerun
					OutputControl,
				outputPPSGenHoldover
					OutputControl,
				outputPPSGenFasttrack
					OutputControl
			 }

		-- 1.3.6.1.4.1.43913.16.8.4.1.1
		outputPPSIndex OBJECT-TYPE
			SYNTAX Integer32 (1)
			MAX-ACCESS not-accessible
			STATUS current
			DESCRIPTION
				"The index of PPS output configuration table."
			::= { outputPPSEntry 1 }


		-- 1.3.6.1.4.1.43913.16.8.4.1.2
		outputPPSState OBJECT-TYPE
			SYNTAX ActionState
			MAX-ACCESS read-write
			STATUS current
			DESCRIPTION
				"Show / Set PPS output state, disable(0), enable(1)."
			::= { outputPPSEntry 2 }


		-- 1.3.6.1.4.1.43913.16.8.4.1.3
		outputPPSGenWarmup OBJECT-TYPE
			SYNTAX OutputControl
			MAX-ACCESS read-write
			STATUS current
			DESCRIPTION
				"Show / Set 10M output generation warm up, squelch(0), on(1)."
			::= { outputPPSEntry 3 }


		-- 1.3.6.1.4.1.43913.16.8.4.1.4
		outputPPSGenFreerun OBJECT-TYPE
			SYNTAX OutputControl
			MAX-ACCESS read-write
			STATUS current
			DESCRIPTION
				"Show / Set 10M output generation free run, squelch(0), on(1)."
			::= { outputPPSEntry 4 }


		-- 1.3.6.1.4.1.43913.16.8.4.1.5
		outputPPSGenHoldover OBJECT-TYPE
			SYNTAX OutputControl
			MAX-ACCESS read-write
			STATUS current
			DESCRIPTION
				"Show / Set 10M output generation hold over, squelch(0), on(1)."
			::= { outputPPSEntry 5 }


		-- 1.3.6.1.4.1.43913.16.8.4.1.6
		outputPPSGenFasttrack OBJECT-TYPE
			SYNTAX OutputControl
			MAX-ACCESS read-write
			STATUS current
			DESCRIPTION
				"Show / Set 10M output generation fast track, squelch(0), on(1)."
			::= { outputPPSEntry 6 }


		-- 1.3.6.1.4.1.43913.16.8.5
		ouputCard OBJECT IDENTIFIER ::= { inputOutput 5 }


		-- 1.3.6.1.4.1.43913.16.8.5.2
		outputCardConfigTable OBJECT-TYPE
			SYNTAX SEQUENCE OF OutputCardConfigEntry
			MAX-ACCESS not-accessible
			STATUS current
			DESCRIPTION
				"Output card configure table."
			::= { ouputCard 2 }


		-- 1.3.6.1.4.1.43913.16.8.5.2.1
		outputCardConfigEntry OBJECT-TYPE
			SYNTAX OutputCardConfigEntry
			MAX-ACCESS not-accessible
			STATUS current
			DESCRIPTION
				"The entry of output card configure table."
			INDEX { outputCardIndex, outputCardSlotID }
			::= { outputCardConfigTable 1 }


		OutputCardConfigEntry ::=
			SEQUENCE {
				outputCardIndex
					Integer32,
				outputCardSlotID
					Integer32,
				outputCardState
					ActionState,
				outputCardE1Signal
					OutputCardE1Signal,
				outputCardE1version
					DisplayString

			 }

		-- 1.3.6.1.4.1.43913.16.8.5.2.1.1
		outputCardIndex OBJECT-TYPE
			SYNTAX Integer32 (0..4)
			MAX-ACCESS not-accessible
			STATUS current
			DESCRIPTION
				"The index of output card configure table."
			::= { outputCardConfigEntry 1 }


		-- 1.3.6.1.4.1.43913.16.8.5.2.1.2
		outputCardSlotID OBJECT-TYPE
			SYNTAX Integer32 (1..14)
			MAX-ACCESS read-only
			STATUS current
			DESCRIPTION
				"Output card slot ID."
			::= { outputCardConfigEntry 2 }


		-- 1.3.6.1.4.1.43913.16.8.5.2.1.3
		outputCardState OBJECT-TYPE
			SYNTAX ActionState
			MAX-ACCESS read-write
			STATUS current
			DESCRIPTION
				"Output card state, disable(0), enable(1)."
			::= { outputCardConfigEntry 3 }


		-- 1.3.6.1.4.1.43913.16.8.5.2.1.4
		outputCardE1Signal OBJECT-TYPE
			SYNTAX OutputCardE1Signal
			MAX-ACCESS read-write
			STATUS current
			DESCRIPTION
				"Output card E1 signal, 2048Khz(0), cas-ccs(1)."
			::= { outputCardConfigEntry 4 }

        -- 1.3.6.1.4.1.43913.16.8.5.2.1.5
		outputCardE1version OBJECT-TYPE
			SYNTAX DisplayString
			MAX-ACCESS read-only
			STATUS current
			DESCRIPTION
				"Output card E1 version."
			::= { outputCardConfigEntry 5 }

		-- 1.3.6.1.4.1.43913.16.8.6
		inputCard OBJECT IDENTIFIER ::= { inputOutput 6 }


		-- 1.3.6.1.4.1.43913.16.8.6.1
		inputCardConfigTable OBJECT-TYPE
			SYNTAX SEQUENCE OF InputCardConfigEntry
			MAX-ACCESS not-accessible
			STATUS current
			DESCRIPTION
				"Input card configuration table."
			::= { inputCard 1 }


		-- 1.3.6.1.4.1.43913.16.8.6.1.1
		inputCardConfigEntry OBJECT-TYPE
			SYNTAX InputCardConfigEntry
			MAX-ACCESS not-accessible
			STATUS current
			DESCRIPTION
				"The entry of input card configuration table."
			INDEX { inputCardIndex }
			::= { inputCardConfigTable 1 }


		InputCardConfigEntry ::=
			SEQUENCE {
				inputCardIndex
					Integer32,
				inputCardSlot
					Integer32,
				inputCardPortID
					Integer32,
				inputCardState
					ActionState,
				inputCardPriority
					Integer32,
				inputCardFrameType
					InputCardFrameType,
				inputCardCRCState
					ActionState,
				inputCardSSMState
					ActionState,
				inputCardSSMBit
					Integer32,
				inputCardPQL
					ClkQL,
				inputCardCfgUsed
					DisplayString
			 }

		-- 1.3.6.1.4.1.43913.16.8.6.1.1.1
		inputCardIndex OBJECT-TYPE
			SYNTAX Integer32 (1..8)
			MAX-ACCESS not-accessible
			STATUS current
			DESCRIPTION
				"The index of input card configuration table."
			::= { inputCardConfigEntry 1 }


		-- 1.3.6.1.4.1.43913.16.8.6.1.1.2
		inputCardSlot OBJECT-TYPE
			SYNTAX Integer32 (1..2)
			MAX-ACCESS read-only
			STATUS current
			DESCRIPTION
				"The slot id of the input card. The value range is 1~2."
			::= { inputCardConfigEntry 2 }


		-- 1.3.6.1.4.1.43913.16.8.6.1.1.3
		inputCardPortID OBJECT-TYPE
			SYNTAX Integer32 (1..4)
			MAX-ACCESS read-only
			STATUS current
			DESCRIPTION
				"The port id of the input card. The value range is 1~4."
			::= { inputCardConfigEntry 3 }


		-- 1.3.6.1.4.1.43913.16.8.6.1.1.4
		inputCardState OBJECT-TYPE
			SYNTAX ActionState
			MAX-ACCESS read-write
			STATUS current
			DESCRIPTION
				"The port state of input card, disable(0) or enable(1)."
			::= { inputCardConfigEntry 4 }


		-- 1.3.6.1.4.1.43913.16.8.6.1.1.5
		inputCardPriority OBJECT-TYPE
			SYNTAX Integer32 (0..20)
			MAX-ACCESS read-write
			STATUS current
			DESCRIPTION
				"The priority of the input."
			::= { inputCardConfigEntry 5 }


		-- 1.3.6.1.4.1.43913.16.8.6.1.1.6
		inputCardFrameType OBJECT-TYPE
			SYNTAX InputCardFrameType
			MAX-ACCESS read-write
			STATUS current
			DESCRIPTION
				"The frame type of input, 1.544MHZ(0), 2.048MHZ(1), CCS(2), CAS(3), D4(4), ESF(5)."
			::= { inputCardConfigEntry 6 }


		-- 1.3.6.1.4.1.43913.16.8.6.1.1.7
		inputCardCRCState OBJECT-TYPE
			SYNTAX ActionState
			MAX-ACCESS read-write
			STATUS current
			DESCRIPTION
				"The CRC state of input, disable(0) or enable(1)."
			::= { inputCardConfigEntry 7 }


		-- 1.3.6.1.4.1.43913.16.8.6.1.1.8
		inputCardSSMState OBJECT-TYPE
			SYNTAX ActionState
			MAX-ACCESS read-write
			STATUS current
			DESCRIPTION
				"The SSM state of input, disable(0) or enable(1)."
			::= { inputCardConfigEntry 8 }


		-- 1.3.6.1.4.1.43913.16.8.6.1.1.9
		inputCardSSMBit OBJECT-TYPE
			SYNTAX Integer32
			MAX-ACCESS read-write
			STATUS current
			DESCRIPTION
				"Input SSM bit."
			::= { inputCardConfigEntry 9 }


		-- 1.3.6.1.4.1.43913.16.8.6.1.1.10
		inputCardPQL OBJECT-TYPE
			SYNTAX ClkQL
			MAX-ACCESS read-write
			STATUS current
			DESCRIPTION
				"Input PQL value."
			::= { inputCardConfigEntry 10 }


		-- 1.3.6.1.4.1.43913.16.8.6.1.1.11
		inputCardCfgUsed OBJECT-TYPE
			SYNTAX DisplayString
			MAX-ACCESS read-only
			STATUS current
			DESCRIPTION
				"The use state of the configration, yes or no."
			::= { inputCardConfigEntry 11 }


		-- 1.3.6.1.4.1.43913.16.8.6.2
		sm2000TrapInputCfg NOTIFICATION-TYPE
			OBJECTS { inputCardSlot, inputCardPortID, inputCardState, inputCardPriority, inputCardFrameType, inputCardCRCState, inputCardSSMState, inputCardSSMBit, inputCardPQL }
			STATUS current
			DESCRIPTION
				"SM2000-5G input configuration trap object which specifies slot ID, port ID and port state / priority / frame type / CRC state / SSM state / SSM bit / input PQL / configuration used state."
			::= { inputCard 2 }

		-- 1.3.6.1.4.1.43913.16.8.6.3



		-- 1.3.6.1.4.1.43913.16.8.7
		outputConfig OBJECT IDENTIFIER ::= { inputOutput 7 }


		-- 1.3.6.1.4.1.43913.16.8.7.1
		outputConfigMainTable OBJECT-TYPE
			SYNTAX SEQUENCE OF OutputConfigMainEntry
			MAX-ACCESS not-accessible
			STATUS current
			DESCRIPTION
				"The output card configuration (main) table."
			::= { outputConfig 1 }


		-- 1.3.6.1.4.1.43913.16.8.7.1.1
		outputConfigMainEntry OBJECT-TYPE
			SYNTAX OutputConfigMainEntry
			MAX-ACCESS not-accessible
			STATUS current
			DESCRIPTION
				"The entry of output card configuration (main) table ."
			INDEX { outputConfigMainIndex, outputConfigMainSlot, outputConfigMainPortID }
			::= { outputConfigMainTable 1 }


		OutputConfigMainEntry ::=
			SEQUENCE {
				outputConfigMainIndex
					Integer32,
				outputConfigMainSlot
					Integer32,
				outputConfigMainPortID
					Integer32,
				outputConfigMainState
					ActionState,
				outputConfigMainFrameType
					OutputCardFrameType,
				outputConfigMainCRCState
					ActionState,
				outputConfigMainSSMState
					ActionState,
				outputConfigMainSSMBit
					OutSSMbitType,
				outputConfigMainTestMode
					OutputCfgTestMode,
				outputConfigMainUsed
					DisplayString,
				outputFreqConfigMainState
					ActionState,
				outputFreqConfigMainFreqType
					OutputFREQtype,
				outputFreqMainReset
					ActionApply,
				outputFreqMainDelay
					Integer32
			 }

		-- 1.3.6.1.4.1.43913.16.8.7.1.1.1
		outputConfigMainIndex OBJECT-TYPE
			SYNTAX Integer32 (0)
			MAX-ACCESS not-accessible
			STATUS current
			DESCRIPTION
				"The index of output card configuration table."
			::= { outputConfigMainEntry 1 }


		-- 1.3.6.1.4.1.43913.16.8.7.1.1.2
		outputConfigMainSlot OBJECT-TYPE
			SYNTAX Integer32 (1..9)
			MAX-ACCESS read-only
			STATUS current
			DESCRIPTION
				"The output card slot id, the range is 1~9."
			::= { outputConfigMainEntry 2 }


		-- 1.3.6.1.4.1.43913.16.8.7.1.1.3
		outputConfigMainPortID OBJECT-TYPE
			SYNTAX Integer32 (1..20)
			MAX-ACCESS read-only
			STATUS current
			DESCRIPTION
				"The port id of the output card, the range is 1~20."
			::= { outputConfigMainEntry 3 }


		-- 1.3.6.1.4.1.43913.16.8.7.1.1.4
		outputConfigMainState OBJECT-TYPE
			SYNTAX ActionState
			MAX-ACCESS read-write
			STATUS current
			DESCRIPTION
				"The state of output, disable(0) or enable(1)."
			::= { outputConfigMainEntry 4 }


		-- 1.3.6.1.4.1.43913.16.8.7.1.1.5
		outputConfigMainFrameType OBJECT-TYPE
			SYNTAX OutputCardFrameType
			MAX-ACCESS read-write
			STATUS current
			DESCRIPTION
				"The frame type of output, 1.544MHZ(0), 2.048MHZ(1), CCS(2), CAS(3), D4(4), ESF(5), 1MHz(6), 5MHz(7), 10MHz(8)."
			::= { outputConfigMainEntry 5 }


		-- 1.3.6.1.4.1.43913.16.8.7.1.1.6
		outputConfigMainCRCState OBJECT-TYPE
			SYNTAX ActionState
			MAX-ACCESS read-write
			STATUS current
			DESCRIPTION
				"The CRC state of output, disable(0) or enable(1)."
			::= { outputConfigMainEntry 6 }


		-- 1.3.6.1.4.1.43913.16.8.7.1.1.7
		outputConfigMainSSMState OBJECT-TYPE
			SYNTAX ActionState
			MAX-ACCESS read-write
			STATUS current
			DESCRIPTION
				"The SSM state of output, disable(0) or enable(1)."
			::= { outputConfigMainEntry 7 }


		-- 1.3.6.1.4.1.43913.16.8.7.1.1.8
		outputConfigMainSSMBit OBJECT-TYPE
			SYNTAX OutSSMbitType
			MAX-ACCESS read-write
			STATUS current
			DESCRIPTION
				"The output SSM bit."
			::= { outputConfigMainEntry 8 }


		-- 1.3.6.1.4.1.43913.16.8.7.1.1.9
		outputConfigMainTestMode OBJECT-TYPE
			SYNTAX OutputCfgTestMode
			MAX-ACCESS read-write
			STATUS current
			DESCRIPTION
				"The output test mode, disable(0), t1pluse(1)."
			::= { outputConfigMainEntry 9 }


		-- 1.3.6.1.4.1.43913.16.8.7.1.1.10
		outputConfigMainUsed OBJECT-TYPE
			SYNTAX DisplayString
			MAX-ACCESS read-only
			STATUS current
			DESCRIPTION
				"The use state of the configration, yes or no."
			::= { outputConfigMainEntry 10 }


		-- 1.3.6.1.4.1.43913.16.8.7.1.1.11
		outputFreqConfigMainState OBJECT-TYPE
			SYNTAX ActionState
			MAX-ACCESS read-write
			STATUS current
			DESCRIPTION
				"The port state of output-freq card, disable(0) or enable(1)."
			::= { outputConfigMainEntry 11 }


		-- 1.3.6.1.4.1.43913.16.8.7.1.1.12
		outputFreqConfigMainFreqType OBJECT-TYPE
			SYNTAX OutputFREQtype
			MAX-ACCESS read-write
			STATUS current
			DESCRIPTION
				"The port frequence type of output-freq card:
					0: 1Hz;  1: 2Hz;  2: 4Hz;  3: 5Hz;  4: 10Hz 5: 20Hz;
					6: 40Hz;  7: 50Hz;  8: 100Hz;  9: 200Hz 10: 400Hz;  11: 500Hz; 12: 800Hz; 13: 1KHz .
					14: 2KHz;  15: 4KHz;  16: 5KHz;  17: 8KHz 18: 10KHz;  19: 20KHz; 20: 40KHz; 21: 50KHz .
					22: 100KHz;  23: 200KHz;  24: 400KHz;  25: 500KHz 26: 1MHz;  27: 2MHz; 28: 4MHz; 29: 5MHz .
					30: 10MHz;  31: 20MHz."
			::= { outputConfigMainEntry 12 }


		-- 1.3.6.1.4.1.43913.16.8.7.1.1.13
		outputFreqMainReset OBJECT-TYPE
			SYNTAX RebootAction
			MAX-ACCESS write-only
			STATUS current
			DESCRIPTION
				"The action of reset output-freq card."
			::= { outputConfigMainEntry 13 }


		-- 1.3.6.1.4.1.43913.16.8.7.1.1.14
		outputFreqMainDelay OBJECT-TYPE
			SYNTAX Integer32 (0..36000000)
			MAX-ACCESS read-write
			STATUS current
			DESCRIPTION
				"The port delay (in unit of 100us) of output-freq card."
			::= { outputConfigMainEntry 14 }

		-- 1.3.6.1.4.1.43913.16.8.7.2
		outputConfigExp1Table OBJECT-TYPE
			SYNTAX SEQUENCE OF OutputConfigExp1Entry
			MAX-ACCESS not-accessible
			STATUS current
			DESCRIPTION
				"The output card configuration (exp1) table."
			::= { outputConfig 2 }


		-- 1.3.6.1.4.1.43913.16.8.7.2.1
		outputConfigExp1Entry OBJECT-TYPE
			SYNTAX OutputConfigExp1Entry
			MAX-ACCESS not-accessible
			STATUS current
			DESCRIPTION
				"The entry of output card configuration (exp1) table ."
			INDEX { outputConfigExp1Index, outputConfigExp1Slot, outputConfigExp1PortID }
			::= { outputConfigExp1Table 1 }


		OutputConfigExp1Entry ::=
			SEQUENCE {
				outputConfigExp1Index
					Integer32,
				outputConfigExp1Slot
					Integer32,
				outputConfigExp1PortID
					Integer32,
				outputConfigExp1State
					ActionState,
				outputConfigExp1FrameType
					OutputCardFrameType,
				outputConfigExp1CRCState
					ActionState,
				outputConfigExp1SSMState
					ActionState,
				outputConfigExp1SSMBit
					OutSSMbitType,
				outputConfigExp1TestMode
					OutputCfgTestMode,
				outputConfigExp1Used
					DisplayString,
				outputFreqConfigExp1State
					ActionState,
				outputFreqConfigExp1FreqType
					OutputFREQtype,
				outputFreqExp1Reset
					ActionApply,
				outputFreqConfigExp1Delay
					Integer32
			 }

		-- 1.3.6.1.4.1.43913.16.8.7.2.1.1
		outputConfigExp1Index OBJECT-TYPE
			SYNTAX Integer32 (1)
			MAX-ACCESS not-accessible
			STATUS current
			DESCRIPTION
				"The index of output card configuration table."
			::= { outputConfigExp1Entry 1 }


		-- 1.3.6.1.4.1.43913.16.8.7.2.1.2
		outputConfigExp1Slot OBJECT-TYPE
			SYNTAX Integer32 (3..14)
			MAX-ACCESS read-only
			STATUS current
			DESCRIPTION
				"The output card slot id, the range is 1~9."
			::= { outputConfigExp1Entry 2 }


		-- 1.3.6.1.4.1.43913.16.8.7.2.1.3
		outputConfigExp1PortID OBJECT-TYPE
			SYNTAX Integer32 (1..20)
			MAX-ACCESS read-only
			STATUS current
			DESCRIPTION
				"The port id of the output card, the range is 1~20."
			::= { outputConfigExp1Entry 3 }


		-- 1.3.6.1.4.1.43913.16.8.7.2.1.4
		outputConfigExp1State OBJECT-TYPE
			SYNTAX ActionState
			MAX-ACCESS read-write
			STATUS current
			DESCRIPTION
				"The state of output, disable(0) or enable(1)."
			::= { outputConfigExp1Entry 4 }


		-- 1.3.6.1.4.1.43913.16.8.7.2.1.5
		outputConfigExp1FrameType OBJECT-TYPE
			SYNTAX OutputCardFrameType
			MAX-ACCESS read-write
			STATUS current
			DESCRIPTION
				"The frame type of output, 1.544MHZ(0), 2.048MHZ(1), CCS(2), CAS(3), D4(4), ESF(5), 1MHz(6), 5MHz(7), 10MHz(8)."
			::= { outputConfigExp1Entry 5 }


		-- 1.3.6.1.4.1.43913.16.8.7.2.1.6
		outputConfigExp1CRCState OBJECT-TYPE
			SYNTAX ActionState
			MAX-ACCESS read-write
			STATUS current
			DESCRIPTION
				"The CRC state of output, disable(0) or enable(1)."
			::= { outputConfigExp1Entry 6 }


		-- 1.3.6.1.4.1.43913.16.8.7.2.1.7
		outputConfigExp1SSMState OBJECT-TYPE
			SYNTAX ActionState
			MAX-ACCESS read-write
			STATUS current
			DESCRIPTION
				"The SSM state of output, disable(0) or enable(1)."
			::= { outputConfigExp1Entry 7 }


		-- 1.3.6.1.4.1.43913.16.8.7.2.1.8
		outputConfigExp1SSMBit OBJECT-TYPE
			SYNTAX OutSSMbitType
			MAX-ACCESS read-write
			STATUS current
			DESCRIPTION
				"The output SSM bit."
			::= { outputConfigExp1Entry 8 }


		-- 1.3.6.1.4.1.43913.16.8.7.2.1.9
		outputConfigExp1TestMode OBJECT-TYPE
			SYNTAX OutputCfgTestMode
			MAX-ACCESS read-write
			STATUS current
			DESCRIPTION
				"The output test mode, disable(0), t1pluse(1)."
			::= { outputConfigExp1Entry 9 }


		-- 1.3.6.1.4.1.43913.16.8.7.2.1.10
		outputConfigExp1Used OBJECT-TYPE
			SYNTAX DisplayString
			MAX-ACCESS read-only
			STATUS current
			DESCRIPTION
				"The use state of the configration, yes or no."
			::= { outputConfigExp1Entry 10 }


		-- 1.3.6.1.4.1.43913.16.8.7.2.1.11
		outputFreqConfigExp1State OBJECT-TYPE
			SYNTAX ActionState
			MAX-ACCESS read-write
			STATUS current
			DESCRIPTION
				"The port state of output-freq card, disable(0) or enable(1)."
			::= { outputConfigExp1Entry 11 }


		-- 1.3.6.1.4.1.43913.16.8.7.2.1.12
		outputFreqConfigExp1FreqType OBJECT-TYPE
			SYNTAX OutputFREQtype
			MAX-ACCESS read-write
			STATUS current
			DESCRIPTION
				"The port frequence type of output-freq card:
					0: 1Hz;  1: 2Hz;  2: 4Hz;  3: 5Hz;  4: 10Hz 5: 20Hz;
					6: 40Hz;  7: 50Hz;  8: 100Hz;  9: 200Hz 10: 400Hz;  11: 500Hz; 12: 800Hz; 13: 1KHz .
					14: 2KHz;  15: 4KHz;  16: 5KHz;  17: 8KHz 18: 10KHz;  19: 20KHz; 20: 40KHz; 21: 50KHz .
					22: 100KHz;  23: 200KHz;  24: 400KHz;  25: 500KHz 26: 1MHz;  27: 2MHz; 28: 4MHz; 29: 5MHz .
					30: 10MHz;  31: 20MHz."
			::= { outputConfigExp1Entry 12 }


		-- 1.3.6.1.4.1.43913.16.8.7.2.1.13
		outputFreqExp1Reset OBJECT-TYPE
			SYNTAX RebootAction
			MAX-ACCESS write-only
			STATUS current
			DESCRIPTION
				"The action of reset output-freq card."
			::= { outputConfigExp1Entry 13 }


		-- 1.3.6.1.4.1.43913.16.8.7.2.1.14
		outputFreqConfigExp1Delay OBJECT-TYPE
			SYNTAX Integer32 (0..36000000)
			MAX-ACCESS read-write
			STATUS current
			DESCRIPTION
				"The port delay (in unit of 100us) of output-freq card."
			::= { outputConfigExp1Entry 14 }


		-- 1.3.6.1.4.1.43913.16.8.7.3
		outputConfigExp2Table OBJECT-TYPE
			SYNTAX SEQUENCE OF OutputConfigExp2Entry
			MAX-ACCESS not-accessible
			STATUS current
			DESCRIPTION
				"The output card configuration (exp2) table."
			::= { outputConfig 3 }


		-- 1.3.6.1.4.1.43913.16.8.7.3.1
		outputConfigExp2Entry OBJECT-TYPE
			SYNTAX OutputConfigExp2Entry
			MAX-ACCESS not-accessible
			STATUS current
			DESCRIPTION
				"The entry of output card configuration (exp2) table ."
			INDEX { outputConfigExp2Index, outputConfigExp2Slot, outputConfigExp2PortID }
			::= { outputConfigExp2Table 1 }


		OutputConfigExp2Entry ::=
			SEQUENCE {
				outputConfigExp2Index
					Integer32,
				outputConfigExp2Slot
					Integer32,
				outputConfigExp2PortID
					Integer32,
				outputConfigExp2State
					ActionState,
				outputConfigExp2FrameType
					OutputCardFrameType,
				outputConfigExp2CRCState
					ActionState,
				outputConfigExp2SSMState
					ActionState,
				outputConfigExp2SSMBit
					OutSSMbitType,
				outputConfigExp2TestMode
					OutputCfgTestMode,
				outputConfigExp2Used
					DisplayString,
				outputFreqConfigExp2State
					ActionState,
				outputFreqConfigExp2FreqType
					OutputFREQtype,
				outputFreqExp2Reset
					ActionApply,
				outputFreqConfigExp2Delay
					Integer32
			 }

		-- 1.3.6.1.4.1.43913.16.8.7.3.1.1
		outputConfigExp2Index OBJECT-TYPE
			SYNTAX Integer32 (2)
			MAX-ACCESS not-accessible
			STATUS current
			DESCRIPTION
				"The index of output card configuration table."
			::= { outputConfigExp2Entry 1 }


		-- 1.3.6.1.4.1.43913.16.8.7.3.1.2
		outputConfigExp2Slot OBJECT-TYPE
			SYNTAX Integer32 (3..14)
			MAX-ACCESS read-only
			STATUS current
			DESCRIPTION
				"The output card slot id, the range is 1~9."
			::= { outputConfigExp2Entry 2 }


		-- 1.3.6.1.4.1.43913.16.8.7.3.1.3
		outputConfigExp2PortID OBJECT-TYPE
			SYNTAX Integer32 (1..20)
			MAX-ACCESS read-only
			STATUS current
			DESCRIPTION
				"The port id of the output card, the range is 1~20."
			::= { outputConfigExp2Entry 3 }


		-- 1.3.6.1.4.1.43913.16.8.7.3.1.4
		outputConfigExp2State OBJECT-TYPE
			SYNTAX ActionState
			MAX-ACCESS read-write
			STATUS current
			DESCRIPTION
				"The state of output, disable(0) or enable(1)."
			::= { outputConfigExp2Entry 4 }


		-- 1.3.6.1.4.1.43913.16.8.7.3.1.5
		outputConfigExp2FrameType OBJECT-TYPE
			SYNTAX OutputCardFrameType
			MAX-ACCESS read-write
			STATUS current
			DESCRIPTION
				"The frame type of output, 1.544MHZ(0), 2.048MHZ(1), CCS(2), CAS(3), D4(4), ESF(5), 1MHz(6), 5MHz(7), 10MHz(8)."
			::= { outputConfigExp2Entry 5 }


		-- 1.3.6.1.4.1.43913.16.8.7.3.1.6
		outputConfigExp2CRCState OBJECT-TYPE
			SYNTAX ActionState
			MAX-ACCESS read-write
			STATUS current
			DESCRIPTION
				"The CRC state of output, disable(0) or enable(1)."
			::= { outputConfigExp2Entry 6 }


		-- 1.3.6.1.4.1.43913.16.8.7.3.1.7
		outputConfigExp2SSMState OBJECT-TYPE
			SYNTAX ActionState
			MAX-ACCESS read-write
			STATUS current
			DESCRIPTION
				"The SSM state of output, disable(0) or enable(1)."
			::= { outputConfigExp2Entry 7 }


		-- 1.3.6.1.4.1.43913.16.8.7.3.1.8
		outputConfigExp2SSMBit OBJECT-TYPE
			SYNTAX OutSSMbitType
			MAX-ACCESS read-write
			STATUS current
			DESCRIPTION
				"The output SSM bit."
			::= { outputConfigExp2Entry 8 }


		-- 1.3.6.1.4.1.43913.16.8.7.3.1.9
		outputConfigExp2TestMode OBJECT-TYPE
			SYNTAX OutputCfgTestMode
			MAX-ACCESS read-write
			STATUS current
			DESCRIPTION
				"The output test mode, disable(0), t1pluse(1)."
			::= { outputConfigExp2Entry 9 }


		-- 1.3.6.1.4.1.43913.16.8.7.3.1.10
		outputConfigExp2Used OBJECT-TYPE
			SYNTAX DisplayString
			MAX-ACCESS read-only
			STATUS current
			DESCRIPTION
				"The use state of the configration, yes or no."
			::= { outputConfigExp2Entry 10 }

		-- 1.3.6.1.4.1.43913.16.8.7.3.1.11
		outputFreqConfigExp2State OBJECT-TYPE
			SYNTAX ActionState
			MAX-ACCESS read-write
			STATUS current
			DESCRIPTION
				"The port state of output-freq card, disable(0) or enable(1)."
			::= { outputConfigExp2Entry 11 }


		-- 1.3.6.1.4.1.43913.16.8.7.3.1.12
		outputFreqConfigExp2FreqType OBJECT-TYPE
			SYNTAX OutputFREQtype
			MAX-ACCESS read-write
			STATUS current
			DESCRIPTION
				"The port frequence type of output-freq card:
					0: 1Hz;  1: 2Hz;  2: 4Hz;  3: 5Hz;  4: 10Hz 5: 20Hz;
					6: 40Hz;  7: 50Hz;  8: 100Hz;  9: 200Hz 10: 400Hz;  11: 500Hz; 12: 800Hz; 13: 1KHz .
					14: 2KHz;  15: 4KHz;  16: 5KHz;  17: 8KHz 18: 10KHz;  19: 20KHz; 20: 40KHz; 21: 50KHz .
					22: 100KHz;  23: 200KHz;  24: 400KHz;  25: 500KHz 26: 1MHz;  27: 2MHz; 28: 4MHz; 29: 5MHz .
					30: 10MHz;  31: 20MHz."
			::= { outputConfigExp2Entry 12 }


		-- 1.3.6.1.4.1.43913.16.8.7.3.1.13
		outputFreqExp2Reset OBJECT-TYPE
			SYNTAX RebootAction
			MAX-ACCESS write-only
			STATUS current
			DESCRIPTION
				"The action of reset output-freq card."
			::= { outputConfigExp2Entry 13 }


		-- 1.3.6.1.4.1.43913.16.8.7.3.1.14
		outputFreqConfigExp2Delay OBJECT-TYPE
			SYNTAX Integer32 (0..36000000)
			MAX-ACCESS read-write
			STATUS current
			DESCRIPTION
				"The port delay (in unit of 100us) of output-freq card."
			::= { outputConfigExp2Entry 14 }


		-- 1.3.6.1.4.1.43913.16.8.7.4
		outputConfigExp3Table OBJECT-TYPE
			SYNTAX SEQUENCE OF OutputConfigExp3Entry
			MAX-ACCESS not-accessible
			STATUS current
			DESCRIPTION
				"The output card configuration (exp3) table."
			::= { outputConfig 4 }


		-- 1.3.6.1.4.1.43913.16.8.7.4.1
		outputConfigExp3Entry OBJECT-TYPE
			SYNTAX OutputConfigExp3Entry
			MAX-ACCESS not-accessible
			STATUS current
			DESCRIPTION
				"The entry of output card configuration (exp3) table ."
			INDEX { outputConfigExp3Index, outputConfigExp3Slot, outputConfigExp3PortID }
			::= { outputConfigExp3Table 1 }


		OutputConfigExp3Entry ::=
			SEQUENCE {
				outputConfigExp3Index
					Integer32,
				outputConfigExp3Slot
					Integer32,
				outputConfigExp3PortID
					Integer32,
				outputConfigExp3State
					ActionState,
				outputConfigExp3FrameType
					OutputCardFrameType,
				outputConfigExp3CRCState
					ActionState,
				outputConfigExp3SSMState
					ActionState,
				outputConfigExp3SSMBit
					OutSSMbitType,
				outputConfigExp3TestMode
					OutputCfgTestMode,
				outputConfigExp3Used
					DisplayString,
				outputFreqConfigExp3State
					ActionState,
				outputFreqConfigExp3FreqType
					OutputFREQtype,
				outputFreqExp3Reset
					ActionApply,
				outputFreqConfigExp3Delay
					Integer32
			 }

		-- 1.3.6.1.4.1.43913.16.8.7.4.1.1
		outputConfigExp3Index OBJECT-TYPE
			SYNTAX Integer32 (3)
			MAX-ACCESS not-accessible
			STATUS current
			DESCRIPTION
				"The index of output card configuration table."
			::= { outputConfigExp3Entry 1 }


		-- 1.3.6.1.4.1.43913.16.8.7.4.1.2
		outputConfigExp3Slot OBJECT-TYPE
			SYNTAX Integer32 (3..14)
			MAX-ACCESS read-only
			STATUS current
			DESCRIPTION
				"The output card slot id, the range is 1~9."
			::= { outputConfigExp3Entry 2 }


		-- 1.3.6.1.4.1.43913.16.8.7.4.1.3
		outputConfigExp3PortID OBJECT-TYPE
			SYNTAX Integer32 (1..20)
			MAX-ACCESS read-only
			STATUS current
			DESCRIPTION
				"The port id of the output card, the range is 1~20."
			::= { outputConfigExp3Entry 3 }


		-- 1.3.6.1.4.1.43913.16.8.7.4.1.4
		outputConfigExp3State OBJECT-TYPE
			SYNTAX ActionState
			MAX-ACCESS read-write
			STATUS current
			DESCRIPTION
				"The state of output, disable(0) or enable(1)."
			::= { outputConfigExp3Entry 4 }


		-- 1.3.6.1.4.1.43913.16.8.7.4.1.5
		outputConfigExp3FrameType OBJECT-TYPE
			SYNTAX OutputCardFrameType
			MAX-ACCESS read-write
			STATUS current
			DESCRIPTION
				"The frame type of output, 1.544MHZ(0), 2.048MHZ(1), CCS(2), CAS(3), D4(4), ESF(5), 1MHz(6), 5MHz(7), 10MHz(8)."
			::= { outputConfigExp3Entry 5 }


		-- 1.3.6.1.4.1.43913.16.8.7.4.1.6
		outputConfigExp3CRCState OBJECT-TYPE
			SYNTAX ActionState
			MAX-ACCESS read-write
			STATUS current
			DESCRIPTION
				"The CRC state of output, disable(0) or enable(1)."
			::= { outputConfigExp3Entry 6 }


		-- 1.3.6.1.4.1.43913.16.8.7.4.1.7
		outputConfigExp3SSMState OBJECT-TYPE
			SYNTAX ActionState
			MAX-ACCESS read-write
			STATUS current
			DESCRIPTION
				"The SSM state of output, disable(0) or enable(1)."
			::= { outputConfigExp3Entry 7 }


		-- 1.3.6.1.4.1.43913.16.8.7.4.1.8
		outputConfigExp3SSMBit OBJECT-TYPE
			SYNTAX OutSSMbitType
			MAX-ACCESS read-write
			STATUS current
			DESCRIPTION
				"The output SSM bit."
			::= { outputConfigExp3Entry 8 }


		-- 1.3.6.1.4.1.43913.16.8.7.4.1.9
		outputConfigExp3TestMode OBJECT-TYPE
			SYNTAX OutputCfgTestMode
			MAX-ACCESS read-write
			STATUS current
			DESCRIPTION
				"The output test mode, disable(0), t1pluse(1)."
			::= { outputConfigExp3Entry 9 }


		-- 1.3.6.1.4.1.43913.16.8.7.4.1.10
		outputConfigExp3Used OBJECT-TYPE
			SYNTAX DisplayString
			MAX-ACCESS read-only
			STATUS current
			DESCRIPTION
				"The use state of the configration, yes or no."
			::= { outputConfigExp3Entry 10 }

		-- 1.3.6.1.4.1.43913.16.8.7.4.1.11
		outputFreqConfigExp3State OBJECT-TYPE
			SYNTAX ActionState
			MAX-ACCESS read-write
			STATUS current
			DESCRIPTION
				"The port state of output-freq card, disable(0) or enable(1)."
			::= { outputConfigExp3Entry 11 }


		-- 1.3.6.1.4.1.43913.16.8.7.4.1.12
		outputFreqConfigExp3FreqType OBJECT-TYPE
			SYNTAX OutputFREQtype
			MAX-ACCESS read-write
			STATUS current
			DESCRIPTION
				"The port frequence type of output-freq card:
					0: 1Hz;  1: 2Hz;  2: 4Hz;  3: 5Hz;  4: 10Hz 5: 20Hz;
					6: 40Hz;  7: 50Hz;  8: 100Hz;  9: 200Hz 10: 400Hz;  11: 500Hz; 12: 800Hz; 13: 1KHz .
					14: 2KHz;  15: 4KHz;  16: 5KHz;  17: 8KHz 18: 10KHz;  19: 20KHz; 20: 40KHz; 21: 50KHz .
					22: 100KHz;  23: 200KHz;  24: 400KHz;  25: 500KHz 26: 1MHz;  27: 2MHz; 28: 4MHz; 29: 5MHz .
					30: 10MHz;  31: 20MHz."
			::= { outputConfigExp3Entry 12 }


		-- 1.3.6.1.4.1.43913.16.8.7.4.1.13
		outputFreqExp3Reset OBJECT-TYPE
			SYNTAX RebootAction
			MAX-ACCESS write-only
			STATUS current
			DESCRIPTION
				"The action of reset output-freq card."
			::= { outputConfigExp3Entry 13 }


		-- 1.3.6.1.4.1.43913.16.8.7.4.1.14
		outputFreqConfigExp3Delay OBJECT-TYPE
			SYNTAX Integer32 (0..36000000)
			MAX-ACCESS read-write
			STATUS current
			DESCRIPTION
				"The port delay (in unit of 100us) of output-freq card."
			::= { outputConfigExp3Entry 14 }


	     -- 1.3.6.1.4.1.43913.16.8.7.5
		outputConfigExp4Table OBJECT-TYPE
			SYNTAX SEQUENCE OF OutputConfigExp4Entry
			MAX-ACCESS not-accessible
			STATUS current
			DESCRIPTION
				"The output card configuration (exp4) table."
			::= { outputConfig 5 }

		-- 1.3.6.1.4.1.43913.16.8.7.5.1
		outputConfigExp4Entry OBJECT-TYPE
			SYNTAX OutputConfigExp4Entry
			MAX-ACCESS not-accessible
			STATUS current
			DESCRIPTION
				"The entry of output card configuration (exp4) table ."
			INDEX { outputConfigExp4Index, outputConfigExp4Slot, outputConfigExp4PortID }
			::= { outputConfigExp4Table 1 }


		OutputConfigExp4Entry ::=
			SEQUENCE {
				outputConfigExp4Index
					Integer32,
				outputConfigExp4Slot
					Integer32,
				outputConfigExp4PortID
					Integer32,
				outputConfigExp4State
					ActionState,
				outputConfigExp4FrameType
					OutputCardFrameType,
				outputConfigExp4CRCState
					ActionState,
				outputConfigExp4SSMState
					ActionState,
				outputConfigExp4SSMBit
					OutSSMbitType,
				outputConfigExp4TestMode
					OutputCfgTestMode,
				outputConfigExp4Used
					DisplayString,
				outputFreqConfigExp4State
					ActionState,
				outputFreqConfigExp4FreqType
					OutputFREQtype,
				outputFreqExp4Reset
					ActionApply,
				outputFreqConfigExp4Delay
					Integer32
			 }

		-- 1.3.6.1.4.1.43913.16.8.7.5.1.1
		outputConfigExp4Index OBJECT-TYPE
			SYNTAX Integer32 (4)
			MAX-ACCESS not-accessible
			STATUS current
			DESCRIPTION
				"The index of output card configuration table."
			::= { outputConfigExp4Entry 1 }


		-- 1.3.6.1.4.1.43913.16.8.7.5.1.2
		outputConfigExp4Slot OBJECT-TYPE
			SYNTAX Integer32 (3..14)
			MAX-ACCESS read-only
			STATUS current
			DESCRIPTION
				"The output card slot id, the range is 1~9."
			::= { outputConfigExp4Entry 2 }


		-- 1.3.6.1.4.1.43913.16.8.7.5.1.3
		outputConfigExp4PortID OBJECT-TYPE
			SYNTAX Integer32 (1..20)
			MAX-ACCESS read-only
			STATUS current
			DESCRIPTION
				"The port id of the output card, the range is 1~20."
			::= { outputConfigExp4Entry 3 }


		-- 1.3.6.1.4.1.43913.16.8.7.5.1.4
		outputConfigExp4State OBJECT-TYPE
			SYNTAX ActionState
			MAX-ACCESS read-write
			STATUS current
			DESCRIPTION
				"The state of output, disable(0) or enable(1)."
			::= { outputConfigExp4Entry 4 }


		-- 1.3.6.1.4.1.43913.16.8.7.5.1.5
		outputConfigExp4FrameType OBJECT-TYPE
			SYNTAX OutputCardFrameType
			MAX-ACCESS read-write
			STATUS current
			DESCRIPTION
				"The frame type of output, 1.544MHZ(0), 2.048MHZ(1), CCS(2), CAS(3), D4(4), ESF(5), 1MHz(6), 5MHz(7), 10MHz(8)."
			::= { outputConfigExp4Entry 5 }


		-- 1.3.6.1.4.1.43913.16.8.7.5.1.6
		outputConfigExp4CRCState OBJECT-TYPE
			SYNTAX ActionState
			MAX-ACCESS read-write
			STATUS current
			DESCRIPTION
				"The CRC state of output, disable(0) or enable(1)."
			::= { outputConfigExp4Entry 6 }


		-- 1.3.6.1.4.1.43913.16.8.7.5.1.7
		outputConfigExp4SSMState OBJECT-TYPE
			SYNTAX ActionState
			MAX-ACCESS read-write
			STATUS current
			DESCRIPTION
				"The SSM state of output, disable(0) or enable(1)."
			::= { outputConfigExp4Entry 7 }


		-- 1.3.6.1.4.1.43913.16.8.7.5.1.8
		outputConfigExp4SSMBit OBJECT-TYPE
			SYNTAX OutSSMbitType
			MAX-ACCESS read-write
			STATUS current
			DESCRIPTION
				"The output SSM bit."
			::= { outputConfigExp4Entry 8 }


		-- 1.3.6.1.4.1.43913.16.8.7.5.1.9
		outputConfigExp4TestMode OBJECT-TYPE
			SYNTAX OutputCfgTestMode
			MAX-ACCESS read-write
			STATUS current
			DESCRIPTION
				"The output test mode, disable(0), t1pluse(1)."
			::= { outputConfigExp4Entry 9 }


		-- 1.3.6.1.4.1.43913.16.8.7.5.1.10
		outputConfigExp4Used OBJECT-TYPE
			SYNTAX DisplayString
			MAX-ACCESS read-only
			STATUS current
			DESCRIPTION
				"The use state of the configration, yes or no."
			::= { outputConfigExp4Entry 10 }


		-- 1.3.6.1.4.1.43913.16.8.7.5.1.11
		outputFreqConfigExp4State OBJECT-TYPE
			SYNTAX ActionState
			MAX-ACCESS read-write
			STATUS current
			DESCRIPTION
				"The port state of output-freq card, disable(0) or enable(1)."
			::= { outputConfigExp4Entry 11 }


		-- 1.3.6.1.4.1.43913.16.8.7.5.1.12
		outputFreqConfigExp4FreqType OBJECT-TYPE
			SYNTAX OutputFREQtype
			MAX-ACCESS read-write
			STATUS current
			DESCRIPTION
				"The port frequence type of output-freq card:
					0: 1Hz;  1: 2Hz;  2: 4Hz;  3: 5Hz;  4: 10Hz 5: 20Hz;
					6: 40Hz;  7: 50Hz;  8: 100Hz;  9: 200Hz 10: 400Hz;  11: 500Hz; 12: 800Hz; 13: 1KHz .
					14: 2KHz;  15: 4KHz;  16: 5KHz;  17: 8KHz 18: 10KHz;  19: 20KHz; 20: 40KHz; 21: 50KHz .
					22: 100KHz;  23: 200KHz;  24: 400KHz;  25: 500KHz 26: 1MHz;  27: 2MHz; 28: 4MHz; 29: 5MHz .
					30: 10MHz;  31: 20MHz."
			::= { outputConfigExp4Entry 12 }


		-- 1.3.6.1.4.1.43913.16.8.7.5.1.13
		outputFreqExp4Reset OBJECT-TYPE
			SYNTAX RebootAction
			MAX-ACCESS write-only
			STATUS current
			DESCRIPTION
				"The action of reset output-freq card."
			::= { outputConfigExp4Entry 13 }


		-- 1.3.6.1.4.1.43913.16.8.7.5.1.14
		outputFreqConfigExp4Delay OBJECT-TYPE
			SYNTAX Integer32 (0..36000000)
			MAX-ACCESS read-write
			STATUS current
			DESCRIPTION
				"The port delay (in unit of 100us) of output-freq card."
			::= { outputConfigExp4Entry 14 }


		 -- 1.3.6.1.4.1.43913.16.8.7.6
		expShelfStatusTable OBJECT-TYPE
			SYNTAX SEQUENCE OF ExpShelfStatusEntry
			MAX-ACCESS not-accessible
			STATUS current
			DESCRIPTION
				"The exp shelf status table."
			::= { outputConfig 6 }

		-- 1.3.6.1.4.1.43913.16.8.7.6.1
		expShelfStatusEntry OBJECT-TYPE
			SYNTAX ExpShelfStatusEntry
			MAX-ACCESS not-accessible
			STATUS current
			DESCRIPTION
				"The entry of exp shelf status table ."
			INDEX { expShelfStatusIndex  }
			::= { expShelfStatusTable 1 }


		ExpShelfStatusEntry ::=
			SEQUENCE {
				expShelfStatusIndex
					Integer32,
				expShelfStatus
					Integer32,
				expShelfCardLedStatus
					DisplayString,
				expShelfCardLedOtherStatus
					OCTET STRING,
				expShelfPortLinkStatus
					OCTET STRING,
				expShelfBufferCardVersion
					DisplayString
			 }

		-- 1.3.6.1.4.1.43913.16.8.7.6.1.1
		expShelfStatusIndex OBJECT-TYPE
			SYNTAX Integer32 (1..4)
			MAX-ACCESS not-accessible
			STATUS current
			DESCRIPTION
				"The index of exp shelf."
			::= { expShelfStatusEntry 1 }

        -- 1.3.6.1.4.1.43913.16.8.7.6.1.2
		expShelfStatus OBJECT-TYPE
			SYNTAX Integer32
			MAX-ACCESS read-only
			STATUS current
			DESCRIPTION
				"The status of exp shelf: 0--Not Connected, 1--Connected"
			::= { expShelfStatusEntry 2 }

		-- 1.3.6.1.4.1.43913.16.8.7.6.1.3
		expShelfCardLedStatus OBJECT-TYPE
			SYNTAX DisplayString
			MAX-ACCESS read-only
			STATUS current
			DESCRIPTION
				"The led status of exp shelf.
				data format:
				buffer1buffer2Output3...Output14
				card type define:
				0: no card, 1: clock card, 2: mgm card, 3: input card, 4: freq out card,
				5: E1 out card, 6: NTP out card, 7: PTP out card, 8: buffer card, 9: PPS-TOD card,
				a: fiber out card, b: 10GE out card
				led status define:
				0: off, 1: red, 2: green, 3: blink green, 4: yellow, 5: blink red, 6: blink yellow
				buffer card data define, 5 bytes:
				cardType,powerA,powerB,sys,activeUse
				out card data define, 3 bytes:
				cardType,power,sys
				NTP out card data define, 7 bytes:
				cardType,power,sys,port1Link,port2Link,port3Link,port4Link"
			::= { expShelfStatusEntry 3 }

		-- 1.3.6.1.4.1.43913.16.8.7.6.1.4
		expShelfCardLedOtherStatus	OBJECT-TYPE
			SYNTAX OCTET STRING
			MAX-ACCESS read-only
			STATUS current
			DESCRIPTION
				"The led other status of exp shelf, 140 bytes:
				10 bytes per card.
				Valid only for ptp/ntp/10GE cards.
				When the ptp/10GE card is used,the first five bytes are the port data.
				ptp/10GE card:
				cardType,port1Link,port2Link,port3Link,port4Link
				When the ntp card is used,the first five bytes are the port data.
				ntp card:
				port1Link,port2Link,port3Link,port4Link,port5Link"
			::= { expShelfStatusEntry 4 }

		-- 1.3.6.1.4.1.43913.16.8.7.6.1.5
		expShelfPortLinkStatus	OBJECT-TYPE
			SYNTAX OCTET STRING
			MAX-ACCESS read-only
			STATUS current
			DESCRIPTION
				"The port link status of exp shelf, 240 bytes:
				bytes0~19 : slot3;
				bytes20~39: slot4;
				......
				bytes220~239: slot14
				Valid only for ptp and ntp cards.
				When the ptp/10GE card is used,the first four bytes are the port link status.
				ptp/10GE card:
				byte[0]=port1Link, byte[1]=port2Link, byte[2]=port3Link, byte[3]=port4Link
				When the ntp card is used,the first five bytes are the port link status.
				ntp card:
				byte[0]=port1Link, byte[1]=port2Link, byte[2]=port3Link, byte[3]=port4Link
				byte[4]=port5Link"
			::= { expShelfStatusEntry 5}

		-- 1.3.6.1.4.1.43913.16.8.7.6.1.6
		expShelfBufferCardVersion	OBJECT-TYPE
			SYNTAX DisplayString
			MAX-ACCESS read-only
			STATUS current
			DESCRIPTION
				"The buffer card verion, format: buffer1 version ; buffer2 version"
			::= { expShelfStatusEntry 6}


	    -- 1.3.6.1.4.1.43913.16.8.7.7
		outputConfigNotifyElements OBJECT IDENTIFIER ::= { outputConfig 7 }


		-- 1.3.6.1.4.1.43913.16.8.7.7.1
		notifyOutputCfgShelf OBJECT-TYPE
			SYNTAX Integer32 (0..4)
			MAX-ACCESS read-only
			STATUS current
			DESCRIPTION
				"Notification of output configuration shelf ID."
			::= { outputConfigNotifyElements 1 }


		-- 1.3.6.1.4.1.43913.16.8.7.7.2
		notifyOutputCfgSlot OBJECT-TYPE
			SYNTAX Integer32 (1..14)
			MAX-ACCESS read-only
			STATUS current
			DESCRIPTION
				"Notification of output configuration slot ID."
			::= { outputConfigNotifyElements 2 }


		-- 1.3.6.1.4.1.43913.16.8.7.7.3
		notifyOutputCfgPort OBJECT-TYPE
			SYNTAX Integer32 (1..16)
			MAX-ACCESS read-only
			STATUS current
			DESCRIPTION
				"Notification of output configuration port ID."
			::= { outputConfigNotifyElements 3 }


		-- 1.3.6.1.4.1.43913.16.8.7.7.4
		notifyOutputCfgState OBJECT-TYPE
			SYNTAX ActionState
			MAX-ACCESS read-only
			STATUS current
			DESCRIPTION
				"Notification of output configuration port state."
			::= { outputConfigNotifyElements 4 }


		-- 1.3.6.1.4.1.43913.16.8.7.7.5
		notifyOutputCfgFrameType OBJECT-TYPE
			SYNTAX OutputCardFrameType
			MAX-ACCESS read-only
			STATUS current
			DESCRIPTION
				"Notification of output configuration frame type."
			::= { outputConfigNotifyElements 5 }


		-- 1.3.6.1.4.1.43913.16.8.7.7.6
		notifyOutputCfgCRCState OBJECT-TYPE
			SYNTAX ActionState
			MAX-ACCESS read-only
			STATUS current
			DESCRIPTION
				"Notification of output configuration CRC state."
			::= { outputConfigNotifyElements 6 }


		-- 1.3.6.1.4.1.43913.16.8.7.7.7
		notifyOutputCfgSSMState OBJECT-TYPE
			SYNTAX ActionState
			MAX-ACCESS read-only
			STATUS current
			DESCRIPTION
				"Notification of output configuration SSM state."
			::= { outputConfigNotifyElements 7 }


		-- 1.3.6.1.4.1.43913.16.8.7.7.8
		notifyOutputCfgSSMBit OBJECT-TYPE
			SYNTAX Integer32
			MAX-ACCESS read-only
			STATUS current
			DESCRIPTION
				"Notification of output configuration SSM bit."
			::= { outputConfigNotifyElements 8 }


		-- 1.3.6.1.4.1.43913.16.8.7.8
		sm2000TrapOutputCfg NOTIFICATION-TYPE
			OBJECTS { notifyOutputCfgShelf, notifyOutputCfgSlot, notifyOutputCfgPort, notifyOutputCfgState, notifyOutputCfgFrameType, notifyOutputCfgCRCState, notifyOutputCfgSSMState, notifyOutputCfgSSMBit }
			STATUS current
			DESCRIPTION
				"SM2000-5G output configuration trap object which specifies shelf ID, slot ID, port ID and port state / frame type / CRC state / SSM state / SSM bit."
			::= { outputConfig 8 }

		-- 1.3.6.1.4.1.43913.16.8.7.9
		sm2000TrapExpShelf NOTIFICATION-TYPE
			OBJECTS { expShelfStatusIndex, expShelfStatus }
			STATUS current
			DESCRIPTION
				"SM2000-5G expand shelf status trap object which specifies expShelfStatusIndex, expShelfStatus."
			::= { outputConfig 9 }



		-- 1.3.6.1.4.1.43913.16.8.8
		ioStatusTable OBJECT-TYPE
			SYNTAX SEQUENCE OF IoStatusEntry
			MAX-ACCESS not-accessible
			STATUS current
			DESCRIPTION
				"Input/output card status table."
			::= { inputOutput 8 }


		-- 1.3.6.1.4.1.43913.16.8.8.1
		ioStatusEntry OBJECT-TYPE
			SYNTAX IoStatusEntry
			MAX-ACCESS not-accessible
			STATUS current
			DESCRIPTION
				"The entry of input/output card status table."
			INDEX { ioStatusIndex, ioStatusSlotID }
			::= { ioStatusTable 1 }


		IoStatusEntry ::=
			SEQUENCE {
				ioStatusIndex
					Integer32,
				ioStatusSlotID
					Integer32,
				ioType
					DisplayString,
				ioSignal
					DisplayString,
				ioStatusRedundancy
					DisplayString,
				ioStatusActive
					DisplayString,
				ioStatusPortCount
					Integer32
			 }

		-- 1.3.6.1.4.1.43913.16.8.8.1.1
		ioStatusIndex OBJECT-TYPE
			SYNTAX Integer32 (0..4)
			MAX-ACCESS not-accessible
			STATUS current
			DESCRIPTION
				"The index of input/output card status table."
			::= { ioStatusEntry 1 }


		-- 1.3.6.1.4.1.43913.16.8.8.1.2
		ioStatusSlotID OBJECT-TYPE
			SYNTAX Integer32  (1..14)
			MAX-ACCESS read-only
			STATUS current
			DESCRIPTION
				"Input/output card slot ID."
			::= { ioStatusEntry 2 }


		-- 1.3.6.1.4.1.43913.16.8.8.1.3
		ioType OBJECT-TYPE
			SYNTAX DisplayString
			MAX-ACCESS read-only
			STATUS current
			DESCRIPTION
				"Input/output card io type, the value is input or output."
			::= { ioStatusEntry 3 }


		-- 1.3.6.1.4.1.43913.16.8.8.1.4
		ioSignal OBJECT-TYPE
			SYNTAX DisplayString
			MAX-ACCESS read-only
			STATUS current
			DESCRIPTION
				"Input/output card io signal, the value is E1-TOD, IRIG, PPS-TOD, E1/2048KHz, E1-T1 or 4-E1."
			::= { ioStatusEntry 4 }


		-- 1.3.6.1.4.1.43913.16.8.8.1.5
		ioStatusRedundancy OBJECT-TYPE
			SYNTAX DisplayString
			MAX-ACCESS read-only
			STATUS current
			DESCRIPTION
				"The redundancy status of output card, the value is disable or enable."
			::= { ioStatusEntry 5 }


		-- 1.3.6.1.4.1.43913.16.8.8.1.6
		ioStatusActive OBJECT-TYPE
			SYNTAX DisplayString
			MAX-ACCESS read-write
			STATUS current
			DESCRIPTION
				"It indicates which card is master or slave card.
				The value of yes means it's a master card,
				and the value of no means it's a slave card."
			::= { ioStatusEntry 6 }

		-- 1.3.6.1.4.1.43913.16.8.8.1.7
		ioStatusPortCount OBJECT-TYPE
			SYNTAX Integer32
			MAX-ACCESS read-only
			STATUS current
			DESCRIPTION
				"The input/output port count of input/output card."
			::= { ioStatusEntry 7 }


		-- 1.3.6.1.4.1.43913.16.8.9
		outputRedundancyTable OBJECT-TYPE
			SYNTAX SEQUENCE OF OutputRedundancyEntry
			MAX-ACCESS not-accessible
			STATUS current
			DESCRIPTION
				"The redundancy configration table of output card."
			::= { inputOutput 9 }


		-- 1.3.6.1.4.1.43913.16.8.9.1
		outputRedundancyEntry OBJECT-TYPE
			SYNTAX OutputRedundancyEntry
			MAX-ACCESS not-accessible
			STATUS current
			DESCRIPTION
				"The entry of output card redundancy configration table."
			INDEX { outRedundancyIndex, outputRedundancySlot }
			::= { outputRedundancyTable 1 }


		OutputRedundancyEntry ::=
			SEQUENCE {
				outRedundancyIndex
					Integer32,
				outputRedundancySlot
					Integer32,
				outputRedundancyState
					ActionState,
				outputRedundancyMode
					RedundMode
			 }

		-- 1.3.6.1.4.1.43913.16.8.9.1.1
		outRedundancyIndex OBJECT-TYPE
			SYNTAX Integer32 (0..4)
			MAX-ACCESS not-accessible
			STATUS current
			DESCRIPTION
				"The index of output card redundancy configration table."
			::= { outputRedundancyEntry 1 }


		-- 1.3.6.1.4.1.43913.16.8.9.1.2
		outputRedundancySlot OBJECT-TYPE
			SYNTAX Integer32 (1..14)
			MAX-ACCESS read-only
			STATUS current
			DESCRIPTION
				"The output card slot number. The range is 2~9."
			::= { outputRedundancyEntry 2 }


		-- 1.3.6.1.4.1.43913.16.8.9.1.3
		outputRedundancyState OBJECT-TYPE
			SYNTAX ActionState
			MAX-ACCESS read-write
			STATUS current
			DESCRIPTION
				"The redundancy state of output card. The value is disable(0) or enable(1)."
			::= { outputRedundancyEntry 3 }


		-- 1.3.6.1.4.1.43913.16.8.9.1.4
		outputRedundancyMode OBJECT-TYPE
			SYNTAX RedundMode
			MAX-ACCESS read-write
			STATUS current
			DESCRIPTION
				"The redundancy mode of output card. The value is 1+1(0) or 1:1(1)."
			::= { outputRedundancyEntry 4 }


		-- 1.3.6.1.4.1.43913.16.8.10
		outputE1GenerationTable OBJECT-TYPE
			SYNTAX SEQUENCE OF OutputE1GenerationEntry
			MAX-ACCESS not-accessible
			STATUS current
			DESCRIPTION
				"The output E1 card generation configration table."
			::= { inputOutput 10 }


		-- 1.3.6.1.4.1.43913.16.8.10.1
		outputE1GenerationEntry OBJECT-TYPE
			SYNTAX OutputE1GenerationEntry
			MAX-ACCESS not-accessible
			STATUS current
			DESCRIPTION
				"The entry of output E1 card generation configration table."
			INDEX { outE1GenerationIndex, outE1Slot}
			::= { outputE1GenerationTable 1 }


		OutputE1GenerationEntry ::=
			SEQUENCE {
				outE1GenerationIndex
					Integer32,
				outE1Slot
					Integer32,
				outE1Warmup
					OutputControlE1,
				outE1Freerun
					OutputControlE1,
				outE1Holdover
					OutputControlE1,
				outE1Fasttrack
					OutputControlE1
			 }

		-- 1.3.6.1.4.1.43913.16.8.10.1.1
		outE1GenerationIndex OBJECT-TYPE
			SYNTAX Integer32 (0..4)
			MAX-ACCESS not-accessible
			STATUS current
			DESCRIPTION
				"The index of output E1 card generation configration table."
			::= { outputE1GenerationEntry 1 }


		-- 1.3.6.1.4.1.43913.16.8.10.1.2
		outE1Slot OBJECT-TYPE
			SYNTAX Integer32 (1..14)
			MAX-ACCESS read-only
			STATUS current
			DESCRIPTION
				"The slot number of output E1 card. The range is 1~9."
			::= { outputE1GenerationEntry 2 }


		-- 1.3.6.1.4.1.43913.16.8.10.1.3
		outE1Warmup OBJECT-TYPE
			SYNTAX OutputControlE1
			MAX-ACCESS read-write
			STATUS current
			DESCRIPTION
				"The warmup configration of output E1 card.
				The value is squelch(0), on(1), or ais(2)."
			::= { outputE1GenerationEntry 3 }


		-- 1.3.6.1.4.1.43913.16.8.10.1.4
		outE1Freerun OBJECT-TYPE
			SYNTAX OutputControlE1
			MAX-ACCESS read-write
			STATUS current
			DESCRIPTION
				"The freerun configration of output E1 card.
				The value is squelch(0), on(1), or ais(2)."
			::= { outputE1GenerationEntry 4 }


		-- 1.3.6.1.4.1.43913.16.8.10.1.5
		outE1Holdover OBJECT-TYPE
			SYNTAX OutputControlE1
			MAX-ACCESS read-write
			STATUS current
			DESCRIPTION
				"The holdover configration of output E1 card.
				The value is squelch(0), on(1), or ais(2)."
			::= { outputE1GenerationEntry 5 }


		-- 1.3.6.1.4.1.43913.16.8.10.1.6
		outE1Fasttrack OBJECT-TYPE
			SYNTAX OutputControlE1
			MAX-ACCESS read-write
			STATUS current
			DESCRIPTION
				"The fasttrack configration of output E1 card.
				The value is squelch(0), on(1), or ais(2)."
			::= { outputE1GenerationEntry 6 }

        -- 1.3.6.1.4.1.43913.16.8.11
		outputPPSTodTable OBJECT-TYPE
			SYNTAX SEQUENCE OF OutputPPSTodEntry
			MAX-ACCESS not-accessible
			STATUS current
			DESCRIPTION
				"The table of pps-tod config."
			::= {inputOutput 11}

	    -- 1.3.6.1.4.1.43913.16.8.11.1
		outputPPSTodEntry OBJECT-TYPE
			SYNTAX  OutputPPSTodEntry
			MAX-ACCESS not-accessible
			STATUS current
			DESCRIPTION
				"The entry of pps-tod config."
			INDEX { outputPPSTodIndex, outputPPSTodSlotIndex }
			::= {outputPPSTodTable 1}

		OutputPPSTodEntry ::=
			SEQUENCE{
				outputPPSTodIndex
					Integer32,
				outputPPSTodSlotIndex
					Integer32,
				outputPPSTodState
					ActionState
			}

		 -- 1.3.6.1.4.1.43913.16.8.11.1.1
		 outputPPSTodIndex OBJECT-TYPE
		 	SYNTAX Integer32 (0..4)
		 	MAX-ACCESS not-accessible
		 	STATUS current
		 	DESCRIPTION
		 		"The pps-tod index: main(0), exp1(1), exp2(2), exp3(3), exp4(4)"
		 	::= {outputPPSTodEntry 1}

		-- 1.3.6.1.4.1.43913.16.8.11.1.2
		outputPPSTodSlotIndex OBJECT-TYPE
			SYNTAX Integer32 (1..14)
		 	MAX-ACCESS not-accessible
		 	STATUS current
		 	DESCRIPTION
		 		"The pps-tod slot index. When the pps-tod index is 0(main), the slot-index range is 1~9;
		 		 When the pps-tod index is 1~4(exp1~exp4), the slot-index range is 3~14"
		 	::= {outputPPSTodEntry 2}

		-- 1.3.6.1.4.1.43913.16.8.11.1.3
		outputPPSTodState OBJECT-TYPE
			SYNTAX ActionState
		 	MAX-ACCESS read-write
		 	STATUS current
		 	DESCRIPTION
		 		"Show / Set the state of pps-tod"
		 	::= {outputPPSTodEntry 3}

        -- 1.3.6.1.4.1.43913.16.8.12
		outputIRIGTable OBJECT-TYPE
			SYNTAX SEQUENCE OF OutputIRIGEntry
			MAX-ACCESS not-accessible
			STATUS current
			DESCRIPTION
				"The table of IRIG config."
			::= {inputOutput 12}

	    -- 1.3.6.1.4.1.43913.16.8.12.1
		outputIRIGEntry OBJECT-TYPE
			SYNTAX  OutputIRIGEntry
			MAX-ACCESS not-accessible
			STATUS current
			DESCRIPTION
				"The entry of IRIG config."
			INDEX { outputIRIGIndex, outputIRIGSlotIndex }
			::= {outputIRIGTable 1}

		OutputIRIGEntry ::=
			SEQUENCE{
				outputIRIGIndex
					Integer32,
				outputIRIGSlotIndex
					Integer32,
				outputIRIGState
					ActionState
			}

		 -- 1.3.6.1.4.1.43913.16.8.12.1.1
		 outputIRIGIndex OBJECT-TYPE
		 	SYNTAX Integer32 (0..4)
		 	MAX-ACCESS not-accessible
		 	STATUS current
		 	DESCRIPTION
		 		"The IRIG index: main(0), exp1(1), exp2(2), exp3(3), exp4(4)"
		 	::= {outputIRIGEntry 1}

		-- 1.3.6.1.4.1.43913.16.8.12.1.2
		outputIRIGSlotIndex OBJECT-TYPE
			SYNTAX Integer32 (1..14)
		 	MAX-ACCESS not-accessible
		 	STATUS current
		 	DESCRIPTION
		 		"The IRIG slot index. When the IRIG index is 0(main), the slot-index range is 1~9;
		 		 When the IRIG index is 1~4(exp1~exp4), the slot-index range is 3~14"
		 	::= {outputIRIGEntry 2}

		-- 1.3.6.1.4.1.43913.16.8.12.1.3
		outputIRIGState OBJECT-TYPE
			SYNTAX ActionState
		 	MAX-ACCESS read-write
		 	STATUS current
		 	DESCRIPTION
		 		"Show / Set the state of IRIG"
		 	::= {outputIRIGEntry 3}


		-- 1.3.6.1.4.1.43913.16.8.13
		outputPTP OBJECT IDENTIFIER ::= { inputOutput 13 }

		-- 1.3.6.1.4.1.43913.16.8.13.1
		outputPTPinventoryTable OBJECT-TYPE
			SYNTAX SEQUENCE OF OutputPTPinventoryEntry
			MAX-ACCESS not-accessible
			STATUS current
			DESCRIPTION
				"The table of output ptp card inventory info."
			::= {outputPTP 1}

	    -- 1.3.6.1.4.1.43913.16.8.13.1.1
		outputPTPinventoryEntry OBJECT-TYPE
			SYNTAX  OutputPTPinventoryEntry
			MAX-ACCESS not-accessible
			STATUS current
			DESCRIPTION
				"The entry of output ptp card inventory info."
			INDEX { outputPTPinventoryShelfIndex, outputPTPinventorySlotIndex }
			::= {outputPTPinventoryTable 1}

		OutputPTPinventoryEntry ::=
			SEQUENCE{
				outputPTPinventoryShelfIndex
					Integer32,
				outputPTPinventorySlotIndex
					Integer32,
				outputPTPinventoryPartNum
					DisplayString,
			    outputPTPinventorySerialNum
			    	DisplayString,
			    outputPTPinventoryCLEINum
			    	DisplayString,
			    outputPTPinventoryHwNum
			    	DisplayString,
			    outputPTPinventorySwNum
			    	DisplayString,
			    outputPTPinventoryFPGAVersion
			    	DisplayString,
			    outputPTPinventoryCompatibilityNum
			    	DisplayString
			}

 	    -- 1.3.6.1.4.1.43913.16.8.13.1.1.1
		outputPTPinventoryShelfIndex OBJECT-TYPE
		 	SYNTAX Integer32 (0..4)
		 	MAX-ACCESS not-accessible
		 	STATUS current
		 	DESCRIPTION
		 		"The index: main(0), exp1(1), exp2(2), exp3(3), exp4(4)"
		 	::= {outputPTPinventoryEntry 1}

	    -- 1.3.6.1.4.1.43913.16.8.13.1.1.2
		outputPTPinventorySlotIndex OBJECT-TYPE
		 	SYNTAX Integer32 (0..14)
		 	MAX-ACCESS not-accessible
		 	STATUS current
		 	DESCRIPTION
		 		"The slot index. When the index is 0(main), the slot-index range is 2~9;
		 		 When the index is 1~4(exp1~exp4), the slot-index range is 3~14"
		 	::= {outputPTPinventoryEntry 2}

		-- 1.3.6.1.4.1.43913.16.8.13.1.1.3
		outputPTPinventoryPartNum OBJECT-TYPE
			SYNTAX DisplayString
			MAX-ACCESS read-only
			STATUS current
			DESCRIPTION
				"The part number of output-ptp card"
		    ::= {outputPTPinventoryEntry 3}

		-- 1.3.6.1.4.1.43913.16.8.13.1.1.4
		outputPTPinventorySerialNum OBJECT-TYPE
			SYNTAX DisplayString
			MAX-ACCESS read-only
			STATUS current
			DESCRIPTION
				"The serial number of output-ptp card"
		    ::= {outputPTPinventoryEntry 4}

		-- 1.3.6.1.4.1.43913.16.8.13.1.1.5
		outputPTPinventoryCLEINum OBJECT-TYPE
			SYNTAX DisplayString
			MAX-ACCESS read-only
			STATUS current
			DESCRIPTION
				"The CLEI number of output-ptp card"
		    ::= {outputPTPinventoryEntry 5}

		-- 1.3.6.1.4.1.43913.16.8.13.1.1.6
		outputPTPinventoryHwNum OBJECT-TYPE
			SYNTAX DisplayString
			MAX-ACCESS read-only
			STATUS current
			DESCRIPTION
				"The hardware number of output-ptp card"
		    ::= {outputPTPinventoryEntry 6}

	    -- 1.3.6.1.4.1.43913.16.8.13.1.1.7
		outputPTPinventorySwNum OBJECT-TYPE
			SYNTAX DisplayString
			MAX-ACCESS read-only
			STATUS current
			DESCRIPTION
				"The software number of output-ptp card"
		    ::= {outputPTPinventoryEntry 7}

	   -- 1.3.6.1.4.1.43913.16.8.13.1.1.8
		outputPTPinventoryFPGAVersion OBJECT-TYPE
			SYNTAX DisplayString
			MAX-ACCESS read-only
			STATUS current
			DESCRIPTION
				"The FPGA version of output-ptp card"
		    ::= {outputPTPinventoryEntry 8}

		-- 1.3.6.1.4.1.43913.16.8.13.1.1.9
		outputPTPinventoryCompatibilityNum OBJECT-TYPE
			SYNTAX DisplayString
			MAX-ACCESS read-only
			STATUS current
			DESCRIPTION
				"The compatibility number of output-ptp card"
		    ::= {outputPTPinventoryEntry 9}


		-- 1.3.6.1.4.1.43913.16.8.13.2
		outputPTPimageTable OBJECT-TYPE
			SYNTAX SEQUENCE OF OutputPTPimageEntry
			MAX-ACCESS not-accessible
			STATUS current
			DESCRIPTION
				"The table of output ptp card image info."
			::= {outputPTP 2}

	    -- 1.3.6.1.4.1.43913.16.8.13.2.1
		outputPTPimageEntry OBJECT-TYPE
			SYNTAX  OutputPTPimageEntry
			MAX-ACCESS not-accessible
			STATUS current
			DESCRIPTION
				"The entry of output ptp card image info."
			INDEX { outputPTPimageShelfIndex, outputPTPimageSlotIndex }
			::= {outputPTPimageTable 1}

		OutputPTPimageEntry ::=
			SEQUENCE{
		       outputPTPimageShelfIndex
		       		Integer32,
		       outputPTPimageSlotIndex
		       		Integer32,
			   outputPTPimageActiveImage
			   		Integer32,
			   outputPTPimageActiveVersion
			   		DisplayString,
			   outputPTPimageBackupImage
			   		Integer32,
			   outputPTPimageBackupVersion
			   		DisplayString,
			   outputPTPimageCurrentImage
			   		Integer32
			 }

	    -- 1.3.6.1.4.1.43913.16.8.13.2.1.1
		outputPTPimageShelfIndex OBJECT-TYPE
		 	SYNTAX Integer32 (0..4)
		 	MAX-ACCESS not-accessible
		 	STATUS current
		 	DESCRIPTION
		 		"The index: main(0), exp1(1), exp2(2), exp3(3), exp4(4)"
		 	::= {outputPTPimageEntry 1}

	    -- 1.3.6.1.4.1.43913.16.8.13.2.1.2
		outputPTPimageSlotIndex OBJECT-TYPE
		 	SYNTAX Integer32 (0..14)
		 	MAX-ACCESS not-accessible
		 	STATUS current
		 	DESCRIPTION
		 		"The slot index. When the index is 0(main), the slot-index range is 2~9;
		 		 When the index is 1~4(exp1~exp4), the slot-index range is 3~14"
		 	::= {outputPTPimageEntry 2}

		-- 1.3.6.1.4.1.43913.16.8.13.2.1.3
		outputPTPimageActiveImage OBJECT-TYPE
			SYNTAX Integer32
			MAX-ACCESS read-only
			STATUS current
			DESCRIPTION
				"The active image id"
			::= {outputPTPimageEntry 3}

		-- 1.3.6.1.4.1.43913.16.8.13.2.1.4
		outputPTPimageActiveVersion OBJECT-TYPE
			SYNTAX DisplayString
			MAX-ACCESS read-only
			STATUS current
			DESCRIPTION
				"The active image version info"
			::= {outputPTPimageEntry 4}

		-- 1.3.6.1.4.1.43913.16.8.13.2.1.5
		outputPTPimageBackupImage OBJECT-TYPE
			SYNTAX Integer32
			MAX-ACCESS read-only
			STATUS current
			DESCRIPTION
				"The backup image id"
			::= {outputPTPimageEntry 5}

		-- 1.3.6.1.4.1.43913.16.8.13.2.1.6
		outputPTPimageBackupVersion OBJECT-TYPE
			SYNTAX DisplayString
			MAX-ACCESS read-only
			STATUS current
			DESCRIPTION
				"The backup image version info"
			::= {outputPTPimageEntry 6}

		-- 1.3.6.1.4.1.43913.16.8.13.2.1.7
		outputPTPimageCurrentImage OBJECT-TYPE
			SYNTAX Integer32  (1..2)
			MAX-ACCESS read-write
			STATUS current
			DESCRIPTION
				"The current next boot up image id."
			::= {outputPTPimageEntry 7}

		-- 1.3.6.1.4.1.43913.16.8.13.3
		outputPTPconfig OBJECT IDENTIFIER ::= { outputPTP 3 }

		-- 1.3.6.1.4.1.43913.16.8.13.3.1
		outputPTPNetworkConfigTable OBJECT-TYPE
			SYNTAX SEQUENCE OF OutputPTPNetworkConfigEntry
			MAX-ACCESS not-accessible
			STATUS current
			DESCRIPTION
				"The table of output ptp card Network config info."
			::= {outputPTPconfig 1}

	    -- 1.3.6.1.4.1.43913.16.8.13.3.1.1
		outputPTPNetworkConfigEntry OBJECT-TYPE
			SYNTAX  OutputPTPNetworkConfigEntry
			MAX-ACCESS not-accessible
			STATUS current
			DESCRIPTION
				"The entry of output ptp card Network config info."
			INDEX { outputPTPNetworkConfigShelfIndex, outputPTPNetworkConfigSlotIndex, outputPTPNetworkConfigPortIndex }
			::= {outputPTPNetworkConfigTable 1}

		OutputPTPNetworkConfigEntry ::=
			SEQUENCE{
		       outputPTPNetworkConfigShelfIndex
		       		Integer32,
		       outputPTPNetworkConfigSlotIndex
		       		Integer32,
		       outputPTPNetworkConfigPortIndex
		            Integer32,
		       outputPTPNetworkConfigIpState
		       		ActionState,
		       outputPTPNetworkConfigIpInfo
		       		DisplayString,
		       outputPTPNetworkConfigVlanMode
		       		ActionState,
		       outputPTPNetworkConfigAutoNegState
		       		ActionState,
		       outputPTPNetworkConfigSpeed
		       		EthLinkSpeedCfg,
		       outputPTPNetworkConfigDuplex
		       		EthlinkDuplexType
		    }

		-- 1.3.6.1.4.1.43913.16.8.13.3.1.1.1
		outputPTPNetworkConfigShelfIndex OBJECT-TYPE
		 	SYNTAX Integer32 (0..4)
		 	MAX-ACCESS not-accessible
		 	STATUS current
		 	DESCRIPTION
		 		"The shelf index: main(0), exp1(1), exp2(2), exp3(3), exp4(4)"
		 	::= {outputPTPNetworkConfigEntry 1}

	    -- 1.3.6.1.4.1.43913.16.8.13.3.1.1.2
		outputPTPNetworkConfigSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::= {outputPTPNetworkConfigEntry 2}

		-- 1.3.6.1.4.1.43913.16.8.13.3.1.1.3
		outputPTPNetworkConfigPortIndex OBJECT-TYPE
		 	SYNTAX Integer32 (1..4)
		 	MAX-ACCESS not-accessible
		 	STATUS current
		 	DESCRIPTION
		 		"The port index: 1~4"
		 	::= {outputPTPNetworkConfigEntry 3}

		-- 1.3.6.1.4.1.43913.16.8.13.3.1.1.4
		outputPTPNetworkConfigIpState  OBJECT-TYPE
			SYNTAX ActionState
			MAX-ACCESS read-write
			STATUS current
			DESCRIPTION
				"The ip state of output-ptp card port. disable(0), enable(1)"
			::={outputPTPNetworkConfigEntry 4}

		-- 1.3.6.1.4.1.43913.16.8.13.3.1.1.5
		outputPTPNetworkConfigIpInfo  OBJECT-TYPE
			SYNTAX DisplayString
			MAX-ACCESS read-write
			STATUS current
			DESCRIPTION
				"The format is : address,netmask,gateway"
			::={outputPTPNetworkConfigEntry 5}

		-- 1.3.6.1.4.1.43913.16.8.13.3.1.1.6
		outputPTPNetworkConfigVlanMode  OBJECT-TYPE
			SYNTAX ActionState
			MAX-ACCESS read-write
			STATUS current
			DESCRIPTION
				"The vlan mode of output-ptp card port. disable(0), enable(1)"
			::={outputPTPNetworkConfigEntry 6}


		-- 1.3.6.1.4.1.43913.16.8.13.3.1.1.7
		outputPTPNetworkConfigAutoNegState  OBJECT-TYPE
			SYNTAX ActionState
			MAX-ACCESS read-write
			STATUS current
			DESCRIPTION
				"The state of output-ptp card auto negotiation. disable(0), enable(1)"
			::={outputPTPNetworkConfigEntry 7}

		-- 1.3.6.1.4.1.43913.16.8.13.3.1.1.8
		outputPTPNetworkConfigSpeed  OBJECT-TYPE
			SYNTAX EthLinkSpeedCfg
			MAX-ACCESS read-write
			STATUS current
			DESCRIPTION
				"The speed of output-ptp card port. 10M(0), 100M(1), 1000M(2), 10000M(3)"
			::={outputPTPNetworkConfigEntry 8}

		-- 1.3.6.1.4.1.43913.16.8.13.3.1.1.9
		outputPTPNetworkConfigDuplex  OBJECT-TYPE
			SYNTAX EthlinkDuplexType
			MAX-ACCESS read-write
			STATUS current
			DESCRIPTION
				"The duplex type of output-ptp card port. full(0), half(1)"
			::={outputPTPNetworkConfigEntry 9}



        -- 1.3.6.1.4.1.43913.16.8.13.3.2
		outputPTPMulticastTable OBJECT-TYPE
			SYNTAX SEQUENCE OF OutputPTPMulticastEntry
			MAX-ACCESS not-accessible
			STATUS current
			DESCRIPTION
				"The table of output ptp card multicast config info."
			::= {outputPTPconfig 2}

	    -- 1.3.6.1.4.1.43913.16.8.13.3.2.1
		outputPTPMulticastEntry OBJECT-TYPE
			SYNTAX  OutputPTPMulticastEntry
			MAX-ACCESS not-accessible
			STATUS current
			DESCRIPTION
				"The entry of output ptp card multicast config info."
			INDEX { outputPTPMulticastShelfIndex,outputPTPMulticastSlotIndex, outputPTPMulticastPortIndex }
			::= {outputPTPMulticastTable 1}

		OutputPTPMulticastEntry ::=
			SEQUENCE{
		       outputPTPMulticastShelfIndex
		       		Integer32,
		       outputPTPMulticastSlotIndex
		       		Integer32,
		       outputPTPMulticastPortIndex
		            Integer32,
               outputPTPMulticastVlanID
              		Integer32,
               outputPTPMulticastSyncIntv
               		Integer32,
               outputPTPMulticastAnnounceIntv
               		Integer32,
               outputPTPMulticastDelayIntv
               		Integer32,
               outputPTPMulticastAnnounceTimeout
               		Integer32,
               outputPTPMulticastClientTimeout
               		Integer32
              }

       -- 1.3.6.1.4.1.43913.16.8.13.3.2.1.1
		outputPTPMulticastShelfIndex OBJECT-TYPE
		 	SYNTAX Integer32 (0..4)
		 	MAX-ACCESS not-accessible
		 	STATUS current
		 	DESCRIPTION
		 		"The shelf index: main(0), exp1(1), exp2(2), exp3(3), exp4(4)"
		 	::= {outputPTPMulticastEntry 1}

	    -- 1.3.6.1.4.1.43913.16.8.13.3.2.1.2
		outputPTPMulticastSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::= {outputPTPMulticastEntry 2}

		-- 1.3.6.1.4.1.43913.16.8.13.3.2.1.3
		outputPTPMulticastPortIndex OBJECT-TYPE
		 	SYNTAX Integer32 (1..4)
		 	MAX-ACCESS not-accessible
		 	STATUS current
		 	DESCRIPTION
		 		"The port index: 1~4"
		 	::= {outputPTPMulticastEntry 3}

        -- 1.3.6.1.4.1.43913.16.8.13.3.2.1.4
        outputPTPMulticastVlanID OBJECT-TYPE
        	SYNTAX Integer32 (0..4094)
            MAX-ACCESS read-write
            STATUS current
            DESCRIPTION
            	"output-ptp card multicast VLAN ID.	"
            ::={outputPTPMulticastEntry 4}


        -- 1.3.6.1.4.1.43913.16.8.13.3.2.1.5
        outputPTPMulticastSyncIntv OBJECT-TYPE
        	SYNTAX Integer32 (-7..7)
            MAX-ACCESS read-write
            STATUS current
            DESCRIPTION
            	"output-ptp card sync interval. -7~7"
            ::={outputPTPMulticastEntry 5}


        -- 1.3.6.1.4.1.43913.16.8.13.3.2.1.6
        outputPTPMulticastAnnounceIntv OBJECT-TYPE
        	SYNTAX Integer32 (-4..4)
            MAX-ACCESS read-write
            STATUS current
            DESCRIPTION
            	"output-ptp card announce interval. -4~4"
            ::={outputPTPMulticastEntry 6}

        -- 1.3.6.1.4.1.43913.16.8.13.3.2.1.7
        outputPTPMulticastDelayIntv OBJECT-TYPE
        	SYNTAX Integer32 (-7..7)
            MAX-ACCESS read-write
            STATUS current
            DESCRIPTION
            	"output-ptp card delay interval. -7~7"
            ::={outputPTPMulticastEntry 7}

        -- 1.3.6.1.4.1.43913.16.8.13.3.2.1.8
        outputPTPMulticastAnnounceTimeout OBJECT-TYPE
        	SYNTAX Integer32 (2..10)
            MAX-ACCESS read-write
            STATUS current
            DESCRIPTION
            	"output-ptp card announce timeout. 2~10"
            ::={outputPTPMulticastEntry 8}

       -- 1.3.6.1.4.1.43913.16.8.13.3.2.1.9
        outputPTPMulticastClientTimeout OBJECT-TYPE
        	SYNTAX Integer32 (10..3600)
            MAX-ACCESS read-write
            STATUS current
            DESCRIPTION
            	"output-ptp card client timeout. 10~3600"
            ::={outputPTPMulticastEntry 9}


        -- 1.3.6.1.4.1.43913.16.8.13.3.3
		outputPTPSynceTable OBJECT-TYPE
			SYNTAX SEQUENCE OF OutputPTPSynceEntry
			MAX-ACCESS not-accessible
			STATUS current
			DESCRIPTION
				"The table of output ptp card SyncE config info."
			::={outputPTPconfig 3}

	    -- 1.3.6.1.4.1.43913.16.8.13.3.3.1
		outputPTPSynceEntry OBJECT-TYPE
			SYNTAX  OutputPTPSynceEntry
			MAX-ACCESS not-accessible
			STATUS current
			DESCRIPTION
				"The entry of output ptp card SyncE config info."
			INDEX { outputPTPSynceShelfIndex, outputPTPSynceSlotIndex, outputPTPSyncePortIndex }
			::={outputPTPSynceTable 1}

		OutputPTPSynceEntry ::=
			SEQUENCE{
		       outputPTPSynceShelfIndex
		       		Integer32,
		       outputPTPSynceSlotIndex
		       		Integer32,
		       outputPTPSyncePortIndex
		            Integer32,
		       outputPTPSynceESMCstate
		       		ActionState,
		       outputPTPSynceQLstate
		       		ActionState,
		       outputPTPSynceOutQLmode
		       		OutputPTPOutQLmode
              }

        -- 1.3.6.1.4.1.43913.16.8.13.3.3.1.1
		outputPTPSynceShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPSynceEntry 1}

	    -- 1.3.6.1.4.1.43913.16.8.13.3.3.1.2
		outputPTPSynceSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={outputPTPSynceEntry 2}

		-- 1.3.6.1.4.1.43913.16.8.13.3.3.1.3
		outputPTPSyncePortIndex OBJECT-TYPE
		 	SYNTAX Integer32 (1..4)
		 	MAX-ACCESS not-accessible
		 	STATUS current
		 	DESCRIPTION
		 		"The port index: 1~4"
		 	::={outputPTPSynceEntry 3}

        -- 1.3.6.1.4.1.43913.16.8.13.3.3.1.4
        outputPTPSynceESMCstate OBJECT-TYPE
        	SYNTAX ActionState
        	MAX-ACCESS read-write
        	STATUS current
        	DESCRIPTION
        		"The ESMC state of SyncE"
        	::={outputPTPSynceEntry 4}

        -- 1.3.6.1.4.1.43913.16.8.13.3.3.1.5
        outputPTPSynceQLstate  OBJECT-TYPE
        	SYNTAX ActionState
        	MAX-ACCESS read-write
        	STATUS current
        	DESCRIPTION
        		"The QL state of SyncE"
        	::={outputPTPSynceEntry 5}

        -- 1.3.6.1.4.1.43913.16.8.13.3.3.1.6
        outputPTPSynceOutQLmode OBJECT-TYPE
        	SYNTAX OutputPTPOutQLmode
        	MAX-ACCESS read-write
        	STATUS current
        	DESCRIPTION
        		"The QL mode of SyncE"
        	::={outputPTPSynceEntry 6}


        -- 1.3.6.1.4.1.43913.16.8.13.3.4
		outputPTPCommonConfig OBJECT IDENTIFIER ::= { outputPTPconfig 4 }

         -- 1.3.6.1.4.1.43913.16.8.13.3.4.1
		outputPTPCommonConfigTable OBJECT-TYPE
			SYNTAX SEQUENCE OF OutputPTPCommonConfigEntry
			MAX-ACCESS not-accessible
			STATUS current
			DESCRIPTION
				"The table of output ptp card common config info."
			::= {outputPTPCommonConfig 1}

	    -- 1.3.6.1.4.1.43913.16.8.13.3.4.1.1
		outputPTPCommonConfigEntry OBJECT-TYPE
			SYNTAX  OutputPTPCommonConfigEntry
			MAX-ACCESS not-accessible
			STATUS current
			DESCRIPTION
				"The entry of output ptp card common config info."
			INDEX { outputPTPCommonConfigShelfIndex, outputPTPCommonConfigSlotIndex, outputPTPCommonConfigPortIndex }
			::= {outputPTPCommonConfigTable 1}

		OutputPTPCommonConfigEntry ::=
			SEQUENCE{
		       outputPTPCommonConfigShelfIndex
		       		Integer32,
		       outputPTPCommonConfigSlotIndex
		       		Integer32,
		       outputPTPCommonConfigPortIndex
		       		Integer32,
		       outputPTPCommonConfigPTPstate
		       		ActionState,
		       outputPTPCommonConfigMaxClients
		       		Integer32,
		       outputPTPCommonConfigProfile
		       		OutputPTPprofile,
		       outputPTPCommonConfigClockID
		       		DisplayString,
		       outputPTPCommonConfigPriority1
		       		Integer32,
		       outputPTPCommonConfigPriority2
		       		Integer32,
		       outputPTPCommonConfigDomain
		       		Integer32,
		       outputPTPCommonConfigDSCP
		       		Integer32,
		       outputPTPCommonConfigDSCPstate
		       		ActionState,
		       outputPTPCommonConfigSyncLimit
		       		Integer32,
		       outputPTPCommonConfigAnnounceLimit
		       		Integer32,
		       outputPTPCommonConfigDelayLimit
		       		Integer32,
		       outputPTPCommonConfigTwoStep
		       		ActionState,
		       outputPTPCommonConfigTTL
		       		Integer32,
		       outputPTPCommonConfigMgmtAddrMode
		       		Integer32,
		       outputPTPCommonConfigAlternateMaster
		       		ActionState,
		       outputPTPCommonConfigUnicastNegotiate
		       		ActionState,
		       outputPTPCommonConfigUnicastLeaseDuration
		       		Integer32,
		       outputPTPCommonConfigDither
		       		Integer32,
		       outputPTPCommonConfigServiceMode
		       		PktServiceType
		    }

		-- 1.3.6.1.4.1.43913.16.8.13.3.4.1.1.1
		outputPTPCommonConfigShelfIndex OBJECT-TYPE
		 	SYNTAX Integer32 (0..4)
		 	MAX-ACCESS not-accessible
		 	STATUS current
		 	DESCRIPTION
		 		"The shelf index: main(0), exp1(1), exp2(2), exp3(3), exp4(4)"
		 	::= {outputPTPCommonConfigEntry 1}

      	-- 1.3.6.1.4.1.43913.16.8.13.3.4.1.1.2
		outputPTPCommonConfigSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::= {outputPTPCommonConfigEntry 2}

        -- 1.3.6.1.4.1.43913.16.8.13.3.4.1.1.3
		outputPTPCommonConfigPortIndex OBJECT-TYPE
		 	SYNTAX Integer32 (1..4)
		 	MAX-ACCESS not-accessible
		 	STATUS current
		 	DESCRIPTION
		 		"The port index. 0~4"
		 	::= {outputPTPCommonConfigEntry 3}


		-- 1.3.6.1.4.1.43913.16.8.13.3.4.1.1.4
		outputPTPCommonConfigPTPstate OBJECT-TYPE
		 	SYNTAX ActionState
		 	MAX-ACCESS read-write
		 	STATUS current
		 	DESCRIPTION
		 		"The state of ptp card"
		 	::= {outputPTPCommonConfigEntry 4}

		-- 1.3.6.1.4.1.43913.16.8.13.3.4.1.1.5
		outputPTPCommonConfigMaxClients OBJECT-TYPE
		 	SYNTAX    Integer32 (1..500)
		 	MAX-ACCESS read-write
		 	STATUS current
		 	DESCRIPTION
		 		"The max client number of ptp card"
		 	::= {outputPTPCommonConfigEntry 5}

		-- 1.3.6.1.4.1.43913.16.8.13.3.4.1.1.6
		outputPTPCommonConfigProfile OBJECT-TYPE
		 	SYNTAX OutputPTPprofile
		 	MAX-ACCESS read-write
		 	STATUS current
		 	DESCRIPTION
		 		"The profile of ptp card. 0: telecom-2008, 1: default,
				3: itu-g8265-1, 4: ethernet-default, 6: itu-g8275-1,
				7: itu-g8275-2, 8: cu-spec, 9: cm-5G-spec"
		 	::= {outputPTPCommonConfigEntry 6}

		 -- 1.3.6.1.4.1.43913.16.8.13.3.4.1.1.7
		outputPTPCommonConfigClockID OBJECT-TYPE
		 	SYNTAX  DisplayString
		 	MAX-ACCESS read-write
		 	STATUS current
		 	DESCRIPTION
		 		"The clock id of ptp card. in format of MAC address: xx:xx:xx:xx:xx:xx:xx:xx"
		 	::= {outputPTPCommonConfigEntry 7}

		-- 1.3.6.1.4.1.43913.16.8.13.3.4.1.1.8
		outputPTPCommonConfigPriority1 OBJECT-TYPE
		 	SYNTAX    Integer32 (0..255)
		 	MAX-ACCESS read-write
		 	STATUS current
		 	DESCRIPTION
		 		"The priority1 of ptp card. Range: 0~255"
		 	::= {outputPTPCommonConfigEntry 8}

		-- 1.3.6.1.4.1.43913.16.8.13.3.4.1.1.9
		outputPTPCommonConfigPriority2 OBJECT-TYPE
		 	SYNTAX    Integer32 (0..255)
		 	MAX-ACCESS read-write
		 	STATUS current
		 	DESCRIPTION
		 		"The priority2 of ptp card. Range: 0~255"
		 	::= {outputPTPCommonConfigEntry 9}

		-- 1.3.6.1.4.1.43913.16.8.13.3.4.1.1.10
		outputPTPCommonConfigDomain OBJECT-TYPE
		 	SYNTAX   Integer32 (0..255)
		 	MAX-ACCESS read-write
		 	STATUS current
		 	DESCRIPTION
		 		"The domain of ptp card. Range: 0~255"
		 	::= {outputPTPCommonConfigEntry 10}

		 -- 1.3.6.1.4.1.43913.16.8.13.3.4.1.1.11
		outputPTPCommonConfigDSCP OBJECT-TYPE
		 	SYNTAX   Integer32 (0..63)
		 	MAX-ACCESS read-write
		 	STATUS current
		 	DESCRIPTION
		 		"The DSCP number of ptp card. Range: 0~63"
		 	::= {outputPTPCommonConfigEntry 11}

		-- 1.3.6.1.4.1.43913.16.8.13.3.4.1.1.12
		outputPTPCommonConfigDSCPstate OBJECT-TYPE
		 	SYNTAX    ActionState
		 	MAX-ACCESS read-write
		 	STATUS current
		 	DESCRIPTION
		 		"The DSCP enable of ptp card. 0: disable, 1: enable"
		 	::= {outputPTPCommonConfigEntry 12}

		-- 1.3.6.1.4.1.43913.16.8.13.3.4.1.1.13
		outputPTPCommonConfigSyncLimit OBJECT-TYPE
		 	SYNTAX    Integer32 (-7..7)
		 	MAX-ACCESS read-write
		 	STATUS current
		 	DESCRIPTION
		 		"The sync limit of ptp card. Range: -7~7"
		 	::= {outputPTPCommonConfigEntry 13}

		-- 1.3.6.1.4.1.43913.16.8.13.3.4.1.1.14
		outputPTPCommonConfigAnnounceLimit OBJECT-TYPE
		 	SYNTAX   Integer32 (-4..4)
		 	MAX-ACCESS read-write
		 	STATUS current
		 	DESCRIPTION
		 		"The announce limit of ptp card. Range: -4~4"
		 	::= {outputPTPCommonConfigEntry 14}

		 -- 1.3.6.1.4.1.43913.16.8.13.3.4.1.1.15
		outputPTPCommonConfigDelayLimit OBJECT-TYPE
		 	SYNTAX   Integer32 (-7..7)
		 	MAX-ACCESS read-write
		 	STATUS current
		 	DESCRIPTION
		 		"The delay limit of ptp card. Range: -7~7"
		 	::= {outputPTPCommonConfigEntry 15}

		-- 1.3.6.1.4.1.43913.16.8.13.3.4.1.1.16
		outputPTPCommonConfigTwoStep OBJECT-TYPE
		 	SYNTAX  ActionState
		 	MAX-ACCESS read-write
		 	STATUS current
		 	DESCRIPTION
		 		"The two-step enable of ptp card. 0: disable, 1: enable"
		 	::= {outputPTPCommonConfigEntry 16}

		-- 1.3.6.1.4.1.43913.16.8.13.3.4.1.1.17
		outputPTPCommonConfigTTL OBJECT-TYPE
		 	SYNTAX  Integer32 (1..255)
		 	MAX-ACCESS read-write
		 	STATUS current
		 	DESCRIPTION
		 		"The ttl of ptp card. range (1~255)"
		 	::= {outputPTPCommonConfigEntry 17}

		-- 1.3.6.1.4.1.43913.16.8.13.3.4.1.1.18
		outputPTPCommonConfigMgmtAddrMode OBJECT-TYPE
		 	SYNTAX   Integer32 (0..1)
		 	MAX-ACCESS read-write
		 	STATUS current
		 	DESCRIPTION
		 		"The management address mode of ptp card. 0: unicast, 1: multicast"
		 	::= {outputPTPCommonConfigEntry 18}

		 -- 1.3.6.1.4.1.43913.16.8.13.3.4.1.1.19
		outputPTPCommonConfigAlternateMaster OBJECT-TYPE
		 	SYNTAX   ActionState
		 	MAX-ACCESS read-write
		 	STATUS current
		 	DESCRIPTION
		 		"The alternate master enable of ptp card. 0: disable, 1: enable"
		 	::= {outputPTPCommonConfigEntry 19}

		-- 1.3.6.1.4.1.43913.16.8.13.3.4.1.1.20
		outputPTPCommonConfigUnicastNegotiate OBJECT-TYPE
		 	SYNTAX    ActionState
		 	MAX-ACCESS read-write
		 	STATUS current
		 	DESCRIPTION
		 		"The unicast negotiate enable of ptp card. 0: disable, 1: enable"
		 	::= {outputPTPCommonConfigEntry 20}

		-- 1.3.6.1.4.1.43913.16.8.13.3.4.1.1.21
		outputPTPCommonConfigUnicastLeaseDuration OBJECT-TYPE
		 	SYNTAX     Integer32 (10..1000)
		 	MAX-ACCESS read-write
		 	STATUS current
		 	DESCRIPTION
		 		"The unicast lease duration of ptp card. Range: 10~1000"
		 	::= {outputPTPCommonConfigEntry 21}

		-- 1.3.6.1.4.1.43913.16.8.13.3.4.1.1.22
		outputPTPCommonConfigDither OBJECT-TYPE
		 	SYNTAX     Integer32 (0..1)
		 	MAX-ACCESS read-write
		 	STATUS current
		 	DESCRIPTION
		 		"The Dither state of ptp output card: enable(1), disable(0)"
		 	::= {outputPTPCommonConfigEntry 22}


		-- 1.3.6.1.4.1.43913.16.8.13.3.4.1.1.23
		outputPTPCommonConfigServiceMode OBJECT-TYPE
		 	SYNTAX     PktServiceType
		 	MAX-ACCESS read-write
		 	STATUS current
		 	DESCRIPTION
		 		"The service type: 0-ptp_gm, 2-ntp_sw, 4-ptp+ntp, 5-ntp_hw"
		 	::= {outputPTPCommonConfigEntry 23}


		-- 1.3.6.1.4.1.43913.16.8.13.3.4.2
		outputPTPCommonOtherConfigTable OBJECT-TYPE
			SYNTAX SEQUENCE OF OutputPTPCommonOtherConfigEntry
			MAX-ACCESS not-accessible
			STATUS current
			DESCRIPTION
				"The table of output ptp other config info."
			::={outputPTPCommonConfig 2}

        -- 1.3.6.1.4.1.43913.16.8.13.3.4.2.1
		outputPTPCommonOtherConfigEntry OBJECT-TYPE
			SYNTAX  OutputPTPCommonOtherConfigEntry
			MAX-ACCESS not-accessible
			STATUS current
			DESCRIPTION
				"The entry of output ptp other config info."
			INDEX { outputPTPCommonOtherConfigShelfIndex, outputPTPCommonOtherConfigSlotIndex }
			::={outputPTPCommonOtherConfigTable 1}

		OutputPTPCommonOtherConfigEntry ::=
			SEQUENCE{
		       outputPTPCommonOtherConfigShelfIndex
		       		Integer32,
		       outputPTPCommonOtherConfigSlotIndex
		       		Integer32,
		       outputPTPCommonOtherConfigTimaScale
		            OutputPTPtimescale
              }

        -- 1.3.6.1.4.1.43913.16.8.13.3.4.2.1.1
		outputPTPCommonOtherConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPCommonOtherConfigEntry 1}

	    -- 1.3.6.1.4.1.43913.16.8.13.3.4.2.1.2
		outputPTPCommonOtherConfigSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={outputPTPCommonOtherConfigEntry 2}

        -- 1.3.6.1.4.1.43913.16.8.13.3.4.2.1.3
        outputPTPCommonOtherConfigTimaScale  OBJECT-TYPE
        	SYNTAX   OutputPTPtimescale
        	MAX-ACCESS read-write
        	STATUS current
        	DESCRIPTION
        		"The timescale of ptp card. 0: auto, 1: arb, 2: ptp"
        	::={outputPTPCommonOtherConfigEntry 3}

        -- 1.3.6.1.4.1.43913.16.8.13.3.5
		outputPTPboardConfigManageTable OBJECT-TYPE
			SYNTAX SEQUENCE OF OutputPTPboardConfigManageEntry
			MAX-ACCESS not-accessible
			STATUS current
			DESCRIPTION
				"The table of output ptp board config management."
			::={outputPTPconfig 5}

        -- 1.3.6.1.4.1.43913.16.8.13.3.5.1
		outputPTPboardConfigManageEntry OBJECT-TYPE
			SYNTAX  OutputPTPboardConfigManageEntry
			MAX-ACCESS not-accessible
			STATUS current
			DESCRIPTION
				"The entry of output ptp board config management."
			INDEX { outputPTPboardConfigManageShelfIndex, outputPTPboardConfigManageSlotIndex }
			::={outputPTPboardConfigManageTable 1}


		OutputPTPboardConfigManageEntry ::=
			SEQUENCE{
		       outputPTPboardConfigManageShelfIndex
		       		Integer32,
		       outputPTPboardConfigManageSlotIndex
		       		Integer32,
		       outputPTPboardConfigManageBackup
		            ActionApply,
		       outputPTPboardConfigManageRestore
		       		Integer32
              }

        -- 1.3.6.1.4.1.43913.16.8.13.3.5.1.1
		outputPTPboardConfigManageShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPboardConfigManageEntry 1}

	    -- 1.3.6.1.4.1.43913.16.8.13.3.5.1.2
		outputPTPboardConfigManageSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPboardConfigManageEntry 2}

        -- 1.3.6.1.4.1.43913.16.8.13.3.5.1.3
        outputPTPboardConfigManageBackup  OBJECT-TYPE
        	SYNTAX   ActionApply
        	MAX-ACCESS read-write
        	STATUS current
        	DESCRIPTION
        		"Backup config of output ptp card locally."
        	::={outputPTPboardConfigManageEntry 3}

        -- 1.3.6.1.4.1.43913.16.8.13.3.5.1.4
        outputPTPboardConfigManageRestore  OBJECT-TYPE
        	SYNTAX   Integer32   (0..1)
        	MAX-ACCESS read-write
        	STATUS current
        	DESCRIPTION
        		"Restore config of output ptp card. 0--dafault config; 1--factory config"
        	::={outputPTPboardConfigManageEntry 4}


     	-- 1.3.6.1.4.1.43913.16.8.13.3.6
		outputPTPntpAuthenticaConfigTable OBJECT-TYPE
			SYNTAX SEQUENCE OF OutputPTPntpAuthenticaConfigEntry
			MAX-ACCESS not-accessible
			STATUS current
			DESCRIPTION
				"The table of output ptp ntp authentica."
			::={outputPTPconfig 6}

        -- 1.3.6.1.4.1.43913.16.8.13.3.6.1
		outputPTPntpAuthenticaConfigEntry OBJECT-TYPE
			SYNTAX  OutputPTPntpAuthenticaConfigEntry
			MAX-ACCESS not-accessible
			STATUS current
			DESCRIPTION
				"The entry of output ptp ntp whitelist."
			INDEX { outputPTPntpAuthenticaConfigShelfIndex, outputPTPntpAuthenticaConfigSlotIndex, outputPTPntpAuthenticaConfigPortIndex }
			::={outputPTPntpAuthenticaConfigTable 1}


		OutputPTPntpAuthenticaConfigEntry ::=
			SEQUENCE{
		       outputPTPntpAuthenticaConfigShelfIndex
		       		Integer32,
		       outputPTPntpAuthenticaConfigSlotIndex
		       		Integer32,
		       outputPTPntpAuthenticaConfigPortIndex
		       		Integer32,
		       outputPTPntpAuthenticaConfigAutokeyState
		       		ActionState,
		       outputPTPntpAuthenticaConfigMD5State
		       		ActionState
              }

        -- 1.3.6.1.4.1.43913.16.8.13.3.7.1.1
		outputPTPntpAuthenticaConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPntpAuthenticaConfigEntry 1}

	    -- 1.3.6.1.4.1.43913.16.8.13.3.6.1.2
		outputPTPntpAuthenticaConfigSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPntpAuthenticaConfigEntry 2}

		-- 1.3.6.1.4.1.43913.16.8.13.3.6.1.3
		outputPTPntpAuthenticaConfigPortIndex OBJECT-TYPE
		 	SYNTAX Integer32 (1..4)
		 	MAX-ACCESS not-accessible
		 	STATUS current
		 	DESCRIPTION
		 		"The port index. "
		 	::={outputPTPntpAuthenticaConfigEntry 3}

        -- 1.3.6.1.4.1.43913.16.8.13.3.6.1.4
        outputPTPntpAuthenticaConfigAutokeyState  OBJECT-TYPE
        	SYNTAX   ActionState
        	MAX-ACCESS read-write
        	STATUS current
        	DESCRIPTION
        		"The state of NTP authentica autokey. enable(1), disable(0)."
        	::={outputPTPntpAuthenticaConfigEntry 4}

       -- 1.3.6.1.4.1.43913.16.8.13.3.6.1.5
        outputPTPntpAuthenticaConfigMD5State  OBJECT-TYPE
        	SYNTAX   ActionState
        	MAX-ACCESS read-write
        	STATUS current
        	DESCRIPTION
        		"The state of NTP authentica MD5. enable(1), disable(0)."
        	::={outputPTPntpAuthenticaConfigEntry 5}



       -- 1.3.6.1.4.1.43913.16.8.13.3.7
		outputPTPntpAuthenticaKeysTable OBJECT-TYPE
			SYNTAX SEQUENCE OF OutputPTPntpAuthenticaKeysEntry
			MAX-ACCESS not-accessible
			STATUS current
			DESCRIPTION
				"The table of output ptp ntp authentica."
			::={outputPTPconfig 7}

        -- 1.3.6.1.4.1.43913.16.8.13.3.7.1
		outputPTPntpAuthenticaKeysEntry OBJECT-TYPE
			SYNTAX  OutputPTPntpAuthenticaKeysEntry
			MAX-ACCESS not-accessible
			STATUS current
			DESCRIPTION
				"The entry of output ptp ntp whitelist."
			INDEX { outputPTPntpAuthenticaKeysShelfIndex, outputPTPntpAuthenticaKeysSlotIndex, outputPTPntpAuthenticaKeysPortIndex }
			::={outputPTPntpAuthenticaKeysTable 1}


		OutputPTPntpAuthenticaKeysEntry ::=
			SEQUENCE{
		       outputPTPntpAuthenticaKeysShelfIndex
		       		Integer32,
		       outputPTPntpAuthenticaKeysSlotIndex
		       		Integer32,
		       outputPTPntpAuthenticaKeysPortIndex
		       		Integer32,
		       outputPTPntpAuthenticaKeysAutokey
		       		DisplayString,
		 	   outputPTPntpAuthenticaKeysMD5key
		       		DisplayString
              }

        -- 1.3.6.1.4.1.43913.16.8.13.3.7.1.1
		outputPTPntpAuthenticaKeysShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPntpAuthenticaKeysEntry 1}

		-- 1.3.6.1.4.1.43913.16.8.13.3.7.1.2
		outputPTPntpAuthenticaKeysSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPntpAuthenticaKeysEntry 2}

		-- 1.3.6.1.4.1.43913.16.8.13.3.7.1.3
		outputPTPntpAuthenticaKeysPortIndex OBJECT-TYPE
		 	SYNTAX Integer32 (1..4)
		 	MAX-ACCESS not-accessible
		 	STATUS current
		 	DESCRIPTION
		 		"The port index."
		 	::={outputPTPntpAuthenticaKeysEntry 3}

       -- 1.3.6.1.4.1.43913.16.8.13.3.7.1.4
        outputPTPntpAuthenticaKeysAutokey  OBJECT-TYPE
        	SYNTAX   DisplayString
        	MAX-ACCESS read-only
        	STATUS current
        	DESCRIPTION
        		"The autokey key value of NTP authentica."
        	::={outputPTPntpAuthenticaKeysEntry 4}

       -- 1.3.6.1.4.1.43913.16.8.13.3.7.1.5
        outputPTPntpAuthenticaKeysMD5key  OBJECT-TYPE
        	SYNTAX   DisplayString
        	MAX-ACCESS read-only
        	STATUS current
        	DESCRIPTION
        		"The MD5 key value of NTP authentica."
        	::={outputPTPntpAuthenticaKeysEntry 5}



       -- 1.3.6.1.4.1.43913.16.8.13.3.8
		outputPTPntplistConfigTable OBJECT-TYPE
			SYNTAX SEQUENCE OF OutputPTPntplistConfigEntry
			MAX-ACCESS not-accessible
			STATUS current
			DESCRIPTION
				"The table of output ptp ntp list state."
			::={outputPTPconfig 8}

        -- 1.3.6.1.4.1.43913.16.8.13.3.8.1
		outputPTPntplistConfigEntry OBJECT-TYPE
			SYNTAX  OutputPTPntplistConfigEntry
			MAX-ACCESS not-accessible
			STATUS current
			DESCRIPTION
				"The entry of output ptp ntp whitelist."
			INDEX { outputPTPntplistConfigShelfIndex, outputPTPntplistConfigSlotIndex, outputPTPntplistConfigPortIndex }
			::={outputPTPntplistConfigTable 1}


		OutputPTPntplistConfigEntry ::=
			SEQUENCE{
		       outputPTPntplistConfigShelfIndex
		       		Integer32,
		       outputPTPntplistConfigSlotIndex
		       		Integer32,
		       outputPTPntplistConfigPortIndex
		       		Integer32,
		       outputPTPntpListState
		       		NtpListState
              }

        -- 1.3.6.1.4.1.43913.16.8.13.3.8.1.1
		outputPTPntplistConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPntplistConfigEntry 1}

	    -- 1.3.6.1.4.1.43913.16.8.13.3.8.1.2
		outputPTPntplistConfigSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPntplistConfigEntry 2}

        -- 1.3.6.1.4.1.43913.16.8.13.3.8.1.3
        outputPTPntplistConfigPortIndex  OBJECT-TYPE
        	SYNTAX   Integer32 (1..4)
        	MAX-ACCESS not-accessible
        	STATUS current
        	DESCRIPTION
        		"The whitelist addr index."
        	::={outputPTPntplistConfigEntry 3}

       -- 1.3.6.1.4.1.43913.16.8.13.3.8.1.4
        outputPTPntpListState  OBJECT-TYPE
        	SYNTAX   NtpListState
        	MAX-ACCESS read-write
        	STATUS current
        	DESCRIPTION
        		"The ntp list state. none(0), whitelist(1), blacklist(2)"
        	::={outputPTPntplistConfigEntry 4}

     	-- 1.3.6.1.4.1.43913.16.8.13.3.9
		outputPTPntpWhitelistTable OBJECT-TYPE
			SYNTAX SEQUENCE OF OutputPTPntpWhitelistEntry
			MAX-ACCESS not-accessible
			STATUS current
			DESCRIPTION
				"The table of output ptp ntp whitelist."
			::={outputPTPconfig 9}

        -- 1.3.6.1.4.1.43913.16.8.13.3.9.1
		outputPTPntpWhitelistEntry OBJECT-TYPE
			SYNTAX  OutputPTPntpWhitelistEntry
			MAX-ACCESS not-accessible
			STATUS current
			DESCRIPTION
				"The entry of output ptp ntp whitelist."
			INDEX { outputPTPntpWhitelistShelfIndex, outputPTPntpWhitelistSlotIndex, outputPTPntpWhitelistPortIndex, outputPTPntpWhitelistIndex }
			::={outputPTPntpWhitelistTable 1}


		OutputPTPntpWhitelistEntry ::=
			SEQUENCE{
		       outputPTPntpWhitelistShelfIndex
		       		Integer32,
		       outputPTPntpWhitelistSlotIndex
		       		Integer32,
		       outputPTPntpWhitelistPortIndex
		       		Integer32,
		       outputPTPntpWhitelistIndex
		       		Integer32,
		       outputPTPntpWhitelistAddr
		       		DisplayString
		       --outputPTPntpWhitelistCount
		       --		Integer32,
		       --outputPTPntpWhitelistRowStatus
		       --		RowStatus
              }

        -- 1.3.6.1.4.1.43913.16.8.13.3.9.1.1
		outputPTPntpWhitelistShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPntpWhitelistEntry 1}

	    -- 1.3.6.1.4.1.43913.16.8.13.3.9.1.2
		outputPTPntpWhitelistSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPntpWhitelistEntry 2}

		-- 1.3.6.1.4.1.43913.16.8.13.3.9.1.3
		outputPTPntpWhitelistPortIndex OBJECT-TYPE
		 	SYNTAX Integer32 (1..4)
		 	MAX-ACCESS not-accessible
		 	STATUS current
		 	DESCRIPTION
		 		"The slot index. "
		 	::={outputPTPntpWhitelistEntry 3}

        -- 1.3.6.1.4.1.43913.16.8.13.3.9.1.4
        outputPTPntpWhitelistIndex  OBJECT-TYPE
        	SYNTAX   Integer32
        	MAX-ACCESS not-accessible
        	STATUS current
        	DESCRIPTION
        		"The whitelist addr index."
        	::={outputPTPntpWhitelistEntry 4}

        -- 1.3.6.1.4.1.43913.16.8.13.3.9.1.5
        outputPTPntpWhitelistAddr  OBJECT-TYPE
        	SYNTAX   DisplayString
        	MAX-ACCESS read-write
        	STATUS current
        	DESCRIPTION
        		"The whitelist addr:
                set format: add,xxx.xxx.xxx.xxx; or add,xxx.xxx.xxx.xxx,xxx.xxx.xxx.xxx;
                            delete,xxx.xxx.xxx.xxx; or delete,xxx.xxx.xxx.xxx,xxx.xxx.xxx.xxx;
                get format: xxx.xxx.xxx.xxx or xxx.xxx.xxx.xxx,xxx.xxx.xxx.xxx;"
        	::={outputPTPntpWhitelistEntry 5}


         -- 1.3.6.1.4.1.43913.16.8.13.3.9.1.6
    --    outputPTPntpWhitelistCount  OBJECT-TYPE
    --    	SYNTAX   Integer32
    --    	MAX-ACCESS read-only
    --    	STATUS current
    --    	DESCRIPTION
    --    		"The whitelist count."
    --    	::={outputPTPntpWhitelistEntry 6}
    --
       	-- 1.3.6.1.4.1.43913.16.8.13.3.9.1.7
    --    outputPTPntpWhitelistRowStatus OBJECT-TYPE
	--		SYNTAX RowStatus
	--		MAX-ACCESS read-write
	--		STATUS current
	--		DESCRIPTION
	--			"The row status of NTP whitelist table to control row actions. It has the following actions:
    --
	--			The status column has six defined values:
    --
	--			     - `active(1)', which indicates that the conceptual row is
	--			     available for use by the managed device;
    --
	--			     - `notInService(2)', which indicates that the conceptual
	--			     row exists in the agent, but is unavailable for use by
	--			     the managed device (see NOTE below);
    --
	--			     - `notReady(3)', which indicates that the conceptual row
	--			     exists in the agent, but is missing information
	--			     necessary in order to be available for use by the
	--			     managed device;
    --
	--			     - `createAndGo(4)', which is supplied by a management
	--			     station wishing to create a new instance of a
	--			     conceptual row and to have its status automatically set
	--			     to active, making it available for use by the managed
	--			     device;
    --
	--			     - `createAndWait(5)', which is supplied by a management
	--			     station wishing to create a new instance of a
	--			     conceptual row (but not make it available for use by
	--			     the managed device); and,
    --
	--			     - `destroy(6)', which is supplied by a management station
	--			     wishing to delete all of the instances associated with
	--			     an existing conceptual row.
	--			"
	--		::= { outputPTPntpWhitelistEntry 7 }



		-- 1.3.6.1.4.1.43913.16.8.13.3.10
		outputPTPntpBlacklistTable OBJECT-TYPE
			SYNTAX SEQUENCE OF OutputPTPntpBlacklistEntry
			MAX-ACCESS not-accessible
			STATUS current
			DESCRIPTION
				"The table of output ptp ntp Blacklist."
			::={outputPTPconfig 10}

        -- 1.3.6.1.4.1.43913.16.8.13.3.10.1
		outputPTPntpBlacklistEntry OBJECT-TYPE
			SYNTAX  OutputPTPntpBlacklistEntry
			MAX-ACCESS not-accessible
			STATUS current
			DESCRIPTION
				"The entry of output ptp ntp Blacklist."
			INDEX { outputPTPntpBlacklistShelfIndex, outputPTPntpBlacklistSlotIndex, outputPTPntpBlacklistPortIndex, outputPTPntpBlacklistIndex }
			::={outputPTPntpBlacklistTable 1}


		OutputPTPntpBlacklistEntry ::=
			SEQUENCE{
		       outputPTPntpBlacklistShelfIndex
		       		Integer32,
		       outputPTPntpBlacklistSlotIndex
		       		Integer32,
		       outputPTPntpBlacklistPortIndex
		       		Integer32,
		       outputPTPntpBlacklistIndex
		       		Integer32,
		       outputPTPntpBlacklistAddr
		       		DisplayString
		       --outputPTPntpBlacklistCount
		       --		Integer32,
		       --outputPTPntpBlacklistRowStatus
		       --		RowStatus
              }

        -- 1.3.6.1.4.1.43913.16.8.13.3.10.1.1
		outputPTPntpBlacklistShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPntpBlacklistEntry 1}

	    -- 1.3.6.1.4.1.43913.16.8.13.3.10.1.2
		outputPTPntpBlacklistSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPntpBlacklistEntry 2}

		-- 1.3.6.1.4.1.43913.16.8.13.3.10.1.3
		outputPTPntpBlacklistPortIndex OBJECT-TYPE
		 	SYNTAX Integer32 (1..4)
		 	MAX-ACCESS not-accessible
		 	STATUS current
		 	DESCRIPTION
		 		"The slot index. "
		 	::={outputPTPntpBlacklistEntry 3}

        -- 1.3.6.1.4.1.43913.16.8.13.3.10.1.4
        outputPTPntpBlacklistIndex  OBJECT-TYPE
        	SYNTAX   Integer32
        	MAX-ACCESS not-accessible
        	STATUS current
        	DESCRIPTION
        		"The Blacklist addr index."
        	::={outputPTPntpBlacklistEntry 4}

        -- 1.3.6.1.4.1.43913.16.8.13.3.10.1.5
        outputPTPntpBlacklistAddr  OBJECT-TYPE
        	SYNTAX   DisplayString
        	MAX-ACCESS read-write
        	STATUS current
        	DESCRIPTION
        		"The Blacklist addr :
                set format: add,xxx.xxx.xxx.xxx; or add,xxx.xxx.xxx.xxx,xxx.xxx.xxx.xxx;
                            delete,xxx.xxx.xxx.xxx; or delete,xxx.xxx.xxx.xxx,xxx.xxx.xxx.xxx;
                get format: xxx.xxx.xxx.xxx or xxx.xxx.xxx.xxx,xxx.xxx.xxx.xxx;"
        	::={outputPTPntpBlacklistEntry 5}

         -- 1.3.6.1.4.1.43913.16.8.13.3.10.1.6
    --    outputPTPntpBlacklistCount  OBJECT-TYPE
    --    	SYNTAX   Integer32
    --    	MAX-ACCESS read-only
    --    	STATUS current
    --    	DESCRIPTION
    --    		"The blacklist count."
    --    	::={outputPTPntpBlacklistEntry 6}
    --
       	-- 1.3.6.1.4.1.43913.16.8.13.3.10.1.7
    --    outputPTPntpBlacklistRowStatus OBJECT-TYPE
	--		SYNTAX RowStatus
	--		MAX-ACCESS read-write
	--		STATUS current
	--		DESCRIPTION
	--			"The row status of NTP Blacklist table to control row actions. It has the following actions:
    --
	--			The status column has six defined values:
    --
	--			     - `active(1)', which indicates that the conceptual row is
	--			     available for use by the managed device;
    --
	--			     - `notInService(2)', which indicates that the conceptual
	--			     row exists in the agent, but is unavailable for use by
	--			     the managed device (see NOTE below);
    --
	--			     - `notReady(3)', which indicates that the conceptual row
	--			     exists in the agent, but is missing information
	--			     necessary in order to be available for use by the
	--			     managed device;
    --
	--			     - `createAndGo(4)', which is supplied by a management
	--			     station wishing to create a new instance of a
	--			     conceptual row and to have its status automatically set
	--			     to active, making it available for use by the managed
	--			     device;
    --
	--			     - `createAndWait(5)', which is supplied by a management
	--			     station wishing to create a new instance of a
	--			     conceptual row (but not make it available for use by
	--			     the managed device); and,
    --
	--			     - `destroy(6)', which is supplied by a management station
	--			     wishing to delete all of the instances associated with
	--			     an existing conceptual row.
	--			"
	--		::= { outputPTPntpBlacklistEntry 7 }

		-- 1.3.6.1.4.1.43913.16.8.13.3.11
		outputPtpRestartTable OBJECT-TYPE
			SYNTAX SEQUENCE OF OutputPtpRestartEntry
			MAX-ACCESS not-accessible
			STATUS current
			DESCRIPTION
				"The table of output ptp restart action."
			::={outputPTPconfig 11}

        -- 1.3.6.1.4.1.43913.16.8.13.3.11.1
		outputPtpRestartEntry OBJECT-TYPE
			SYNTAX  OutputPtpRestartEntry
			MAX-ACCESS not-accessible
			STATUS current
			DESCRIPTION
				"The entry of output ptp restart action."
			INDEX { outputPtpRestartShelfIndex, outputPtpRestartSlotIndex, outputPtpRestartPortIndex }
			::={outputPtpRestartTable 1}


		OutputPtpRestartEntry ::=
			SEQUENCE{
		       outputPtpRestartShelfIndex
		       		Integer32,
		       outputPtpRestartSlotIndex
		       		Integer32,
		       outputPtpRestartPortIndex
		       		Integer32,
		       outputPtpRestartAction
		       		ActionApply,
		       outputPtpRestartResult
		       		ActionResult
              }

        -- 1.3.6.1.4.1.43913.16.8.13.3.11.1.1
		outputPtpRestartShelfIndex OBJECT-TYPE
		 	SYNTAX Integer32 (0..4)
		 	MAX-ACCESS not-accessible
		 	STATUS current
		 	DESCRIPTION
		 		"The shelf index: main(0), exp1(1), exp2(2), exp3(3), exp4(4)"
		 	::={outputPtpRestartEntry 1}

		-- 1.3.6.1.4.1.43913.16.8.13.3.11.1.2
		outputPtpRestartSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPtpRestartEntry 2}

		-- 1.3.6.1.4.1.43913.16.8.13.3.11.1.3
		outputPtpRestartPortIndex OBJECT-TYPE
		 	SYNTAX Integer32 (0..4)
		 	MAX-ACCESS not-accessible
		 	STATUS current
		 	DESCRIPTION
		 		"The port index. 0 means the card, 1~4 means the port index"
		 	::={outputPtpRestartEntry 3}

		-- 1.3.6.1.4.1.43913.16.8.13.3.11.1.4
		outputPtpRestartAction OBJECT-TYPE
		 	SYNTAX RebootAction
		 	MAX-ACCESS read-write
		 	STATUS current
		 	DESCRIPTION
		 		" Restart output PTP card"
		 	::={outputPtpRestartEntry 4}

		-- 1.3.6.1.4.1.43913.16.8.13.3.11.1.5
		outputPtpRestartResult OBJECT-TYPE
		 	SYNTAX ActionResult
		 	MAX-ACCESS read-only
		 	STATUS current
		 	DESCRIPTION
		 		" success(1), fail(2)"
		 	::={outputPtpRestartEntry 5}

		-- 1.3.6.1.4.1.43913.16.8.13.3.11
		outputPtpTimestampDelayTable OBJECT-TYPE
			SYNTAX SEQUENCE OF OutputPtpTimestampDelayEntry
			MAX-ACCESS not-accessible
			STATUS current
			DESCRIPTION
				"The table of output ptp timestamp delay."
			::={outputPTPconfig 12}

        -- 1.3.6.1.4.1.43913.16.8.13.3.11.1
		outputPtpTimestampDelayEntry OBJECT-TYPE
			SYNTAX  OutputPtpTimestampDelayEntry
			MAX-ACCESS not-accessible
			STATUS current
			DESCRIPTION
				"The entry of output ptp timestamp delay."
			INDEX { outputPtpTimestampDelayShelfIndex, outputPtpTimestampDelaySlotIndex }
			::={outputPtpTimestampDelayTable 1}


		OutputPtpTimestampDelayEntry ::=
			SEQUENCE{
		       outputPtpTimestampDelayShelfIndex
		       		Integer32,
		       outputPtpTimestampDelaySlotIndex
		       		Integer32,
		       outputPtpTimestampDelay
		       		DisplayString
              }

        -- 1.3.6.1.4.1.43913.16.8.13.3.11.1.1
		outputPtpTimestampDelayShelfIndex OBJECT-TYPE
		 	SYNTAX Integer32 (0..4)
		 	MAX-ACCESS not-accessible
		 	STATUS current
		 	DESCRIPTION
		 		"The shelf index: main(0), exp1(1), exp2(2), exp3(3), exp4(4)"
		 	::={outputPtpTimestampDelayEntry 1}

		-- 1.3.6.1.4.1.43913.16.8.13.3.11.1.2
		outputPtpTimestampDelaySlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPtpTimestampDelayEntry 2}

		-- 1.3.6.1.4.1.43913.16.8.13.3.11.1.4
		outputPtpTimestampDelay OBJECT-TYPE
		 	SYNTAX DisplayString
		 	MAX-ACCESS read-write
		 	STATUS current
		 	DESCRIPTION
		 		"Output PTP card timestamp delay.
                unit : ns
                get format: d1;d2;d3;d4;...,d24;
                port1 OPTI-1000M TX : d1
                port1 ELEC-100M  TX : d2
                port1 ELEC-1000M TX : d3
                port1 OPTI-1000M RX : d4
                port1 ELEC-100M  RX : d5
                port1 ELEC-1000M RX : d6
                set format: port,sfp_type,rt_tpye,delay;
                port     : 1~4
                sfp_type : 0-OPTI,1-ELEC-100M,2-ELEC-1000M
                rt_tpye  : 0-TX,1-RX
                delay    : 0~65535
				Output 10GE card timestamp delay.
                unit : ns
                get format: d1;d2;d3;d4;...,d32;
                port1 OPTI-1000M TX : d1
                port1 ELEC-100M  TX : d2
                port1 ELEC-1000M TX : d3
                port1 OPTI-10000M TX : d4
                port1 OPTI-1000M RX : d5
                port1 ELEC-100M  RX : d6
                port1 ELEC-1000M RX : d7
                port1 OPTI-10000M RX : d8
                set format: port,sfp_type,rt_tpye,delay;
                port     : 1~4
                sfp_type : 0-OPTI,1-ELEC-100M,2-ELEC-1000M,3-OPTI-10000M
                rt_tpye  : 0-TX,1-RX
                delay    : 0~65535"
		 	::={outputPtpTimestampDelayEntry 3}

		-- 1.3.6.1.4.1.43913.16.8.13.3.10
		outputPTPVlanConfigTable OBJECT-TYPE
			SYNTAX SEQUENCE OF OutputPTPVlanConfigEntry
			MAX-ACCESS not-accessible
			STATUS current
			DESCRIPTION
				"The table of output ptp vlan config."
			::={outputPTPconfig 13}

        -- 1.3.6.1.4.1.43913.16.8.13.3.10.1
		outputPTPVlanConfigEntry OBJECT-TYPE
			SYNTAX  OutputPTPVlanConfigEntry
			MAX-ACCESS not-accessible
			STATUS current
			DESCRIPTION
				"The entry of output ptp vlan config."
			INDEX { outputPTPVlanShelfIndex, outputPTPVlanSlotIndex, outputPTPVlanPortIndex, outputPTPVlanIndex }
			::={outputPTPVlanConfigTable 1}

		OutputPTPVlanConfigEntry ::=
			SEQUENCE{
		       outputPTPVlanShelfIndex
		       		Integer32,
		       outputPTPVlanSlotIndex
		       		Integer32,
		       outputPTPVlanPortIndex
		       		Integer32,
		       outputPTPVlanIndex
		       		Integer32,
		       outputPTPVlanInfo
		       		DisplayString,
		       outputPTPVlanState
		       		Integer32
              }

        -- 1.3.6.1.4.1.43913.16.8.13.3.10.1.1
		outputPTPVlanShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPVlanConfigEntry 1}

	    -- 1.3.6.1.4.1.43913.16.8.13.3.10.1.2
		outputPTPVlanSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPVlanConfigEntry 2}

		-- 1.3.6.1.4.1.43913.16.8.13.3.10.1.3
		outputPTPVlanPortIndex OBJECT-TYPE
		 	SYNTAX Integer32 (1..4)
		 	MAX-ACCESS not-accessible
		 	STATUS current
		 	DESCRIPTION
		 		"The port index. "
		 	::={outputPTPVlanConfigEntry 3}

        -- 1.3.6.1.4.1.43913.16.8.13.3.10.1.4
        outputPTPVlanIndex  OBJECT-TYPE
        	SYNTAX   Integer32
        	MAX-ACCESS not-accessible
        	STATUS current
        	DESCRIPTION
        		"The vlan index. The vlan index range is 1~16."
        	::={outputPTPVlanConfigEntry 4}

        -- 1.3.6.1.4.1.43913.16.8.13.3.10.1.5
        outputPTPVlanInfo  OBJECT-TYPE
        	SYNTAX   DisplayString
        	MAX-ACCESS read-write
        	STATUS current
        	DESCRIPTION
        		"Get and set vlan config.
                get data format: vlan-id,vlan-pri,ipaddr,netmask,gateway;
                set format:
                set vlan: add,vlan-id,vlan-pri,ipaddr,netmask,gateway;
                modify vlan ip: modify,ipaddr,netmask,gateway;
                delete vlan config: delete;"
        	::={outputPTPVlanConfigEntry 5}

        -- 1.3.6.1.4.1.43913.16.8.13.3.10.1.6
        outputPTPVlanState  OBJECT-TYPE
        	SYNTAX   Integer32
        	MAX-ACCESS read-write
        	STATUS current
        	DESCRIPTION
        		"The vlan config state config.
                The vlan state. 0: disable, 1: enable"
        	::={outputPTPVlanConfigEntry 6}

        -- 1.3.6.1.4.1.43913.16.8.14.3.5
		outputPTPntpConfigTable OBJECT-TYPE
			SYNTAX SEQUENCE OF OutputPTPntpConfigEntry
			MAX-ACCESS not-accessible
			STATUS current
			DESCRIPTION
				"The table of output ptp ntp config management."
			::={outputPTPconfig 14}

        -- 1.3.6.1.4.1.43913.16.8.14.3.5.1
		outputPTPntpConfigEntry OBJECT-TYPE
			SYNTAX  OutputPTPntpConfigEntry
			MAX-ACCESS not-accessible
			STATUS current
			DESCRIPTION
				"The entry of output ptp board config management."
			INDEX { outputPTPntpConfigShelfIndex, outputPTPntpConfigSlotIndex }
			::={outputPTPntpConfigTable 1}

		OutputPTPntpConfigEntry ::=
			SEQUENCE{
		       outputPTPntpConfigShelfIndex
		       		Integer32,
		       outputPTPntpConfigSlotIndex
		       		Integer32,
		       outputPTPntpConfigIpvx
		            OutputPTPntpIpvx,
		       outputPTPntpConfigType
		       		OutputPTPntpType
              }

        -- 1.3.6.1.4.1.43913.16.8.14.3.5.1.1
		outputPTPntpConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPntpConfigEntry 1}

	    -- 1.3.6.1.4.1.43913.16.8.13.3.5.1.2
		outputPTPntpConfigSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPntpConfigEntry 2}

        -- 1.3.6.1.4.1.43913.16.8.14.3.5.1.3
        outputPTPntpConfigIpvx  OBJECT-TYPE
        	SYNTAX OutputPTPntpIpvx
        	MAX-ACCESS read-write
        	STATUS current
        	DESCRIPTION
        		"ntp config of output ptp card. When the ntp-type is ntp_hw, this node is used;
				0--ntp ipv4; 1--ntp ipv6"
        	::={outputPTPntpConfigEntry 3}

        -- 1.3.6.1.4.1.43913.16.8.14.3.5.1.4
        outputPTPntpConfigType  OBJECT-TYPE
        	SYNTAX OutputPTPntpType
        	MAX-ACCESS read-write
        	STATUS current
        	DESCRIPTION
        		"ntp config of output ptp card. 0--ntp software; 1--ntp hardware"
        	::={outputPTPntpConfigEntry 4}

		-- 1.3.6.1.4.1.43913.16.8.13.3.15
		outputPTPcardRedundancy OBJECT-TYPE
			SYNTAX DisplayString
			MAX-ACCESS read-write
			STATUS current
			DESCRIPTION
				"set PTP/10GE out card redundancy state.
				set format: a,b,c,d;
				a : state
				b : 0 ~ 4  (shelf)
				c : 0 ~ 14 (slot)
				d : 0 ~ 1  (enable/disable)
				set PTP/10GE out card get redundancy status index.
				set format: a,b,c,d;
				a : index
				b : 0 ~ 4  (shelf)
				c : 0 ~ 14 (slot)
				d : 0
				get PTP/10GE out card redundancy status.
				get data format: p1;p2;p3;
				p1 format : a,b
				a : 0 ~ 4  (shelf)
				b : 0 ~ 14 (slot)
				p2/p3 format : a,b,c,m1,m2,m3,m4;
				a : 0 ~ 1 (redundancy state)
				b : 0 ~ 1 (redundancy mode)
				c : 0 ~ 1 (redundancy peer exist)
				m1-4 : port1-4 mac addr
				"
			::= { outputPTPconfig 15 }

		--	1.3.6.1.4.1.43913.16.8.13.3.16
		outputPTPportRedundancy OBJECT-TYPE
			SYNTAX DisplayString
			MAX-ACCESS read-write
			STATUS current
			DESCRIPTION
				"set PTP/10GE out port redundancy state.
				set format: a,b,c,d,e;
				a : state
				b : 0 ~ 4  (shelf)
				c : 0 ~ 14 (slot)
				d : 0 ~ 1  (port-1-2/port-3-4)
				e : 0 ~ 1  (enable/disable)
				set PTP/10GE out port get redundancy index.
				set format: a,b,c,d,e;
				a : index
				b : 0 ~ 4  (shelf)
				c : 0 ~ 14 (slot)
				d : 0
				e : 0
				get PTP/10GE out port redundancy status.
				get data format: p1;p2;p3;
				p1 format : a,b;
				a : 0 ~ 4  (shelf)
				b : 0 ~ 14 (slot)
				p2/p3 format : a,b
				a : 0 ~ 1   (bonding state)
				b : 0/1/255 (active port/error)
				"
			::= { outputPTPconfig 16 }

        -- 1.3.6.1.4.1.43913.16.8.13.4
		outputPTPstatus OBJECT IDENTIFIER ::= { outputPTP 4 }

        -- 1.3.6.1.4.1.43913.16.8.13.4.1
		outputPTPSynceStatusTable OBJECT-TYPE
			SYNTAX SEQUENCE OF OutputPTPSynceStatusEntry
			MAX-ACCESS not-accessible
			STATUS current
			DESCRIPTION
				"The table of output ptp card SyncE status info."
			::={outputPTPstatus 1}

	    -- 1.3.6.1.4.1.43913.16.8.13.4.1.1
		outputPTPSynceStatusEntry OBJECT-TYPE
			SYNTAX  OutputPTPSynceStatusEntry
			MAX-ACCESS not-accessible
			STATUS current
			DESCRIPTION
				"The entry of output ptp card SyncE config info."
			INDEX { outputPTPSynceStatusShelfIndex, outputPTPSynceStatusSlotIndex, outputPTPSynceStatusPortIndex }
			::={outputPTPSynceStatusTable 1}

		OutputPTPSynceStatusEntry ::=
			SEQUENCE{
		       outputPTPSynceStatusShelfIndex
		       		Integer32,
		       outputPTPSynceStatusSlotIndex
		       		Integer32,
		       outputPTPSynceStatusPortIndex
		            	Integer32,
		       outputPTPSynceStatusEthMode
		       		DisplayString,
		       outputPTPSynceStatusESMCstatus
		       		DisplayString,
		       outputPTPSynceStatusTXssm
		       		DisplayString
              }

        -- 1.3.6.1.4.1.43913.16.8.13.4.1.1.1
		outputPTPSynceStatusShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPSynceStatusEntry 1}

	    -- 1.3.6.1.4.1.43913.16.8.13.4.1.1.2
		outputPTPSynceStatusSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={outputPTPSynceStatusEntry 2}

		-- 1.3.6.1.4.1.43913.16.8.13.4.1.1.3
		outputPTPSynceStatusPortIndex OBJECT-TYPE
		 	SYNTAX Integer32 (1..4)
		 	MAX-ACCESS not-accessible
		 	STATUS current
		 	DESCRIPTION
		 		"The port index: 1~4"
		 	::={outputPTPSynceStatusEntry 3}

        -- 1.3.6.1.4.1.43913.16.8.13.4.1.1.4
        outputPTPSynceStatusEthMode OBJECT-TYPE
		 	SYNTAX DisplayString
		 	MAX-ACCESS read-only
		 	STATUS current
		 	DESCRIPTION
		 		"The eth mode of SyncE status"
		 	::={outputPTPSynceStatusEntry 4}

        -- 1.3.6.1.4.1.43913.16.8.13.4.1.1.5
        outputPTPSynceStatusESMCstatus OBJECT-TYPE
		 	SYNTAX DisplayString
		 	MAX-ACCESS read-only
		 	STATUS current
		 	DESCRIPTION
		 		"The eth mode of SyncE status"
		 	::={outputPTPSynceStatusEntry 5}

        -- 1.3.6.1.4.1.43913.16.8.13.4.1.1.6
        outputPTPSynceStatusTXssm OBJECT-TYPE
		 	SYNTAX DisplayString
		 	MAX-ACCESS read-only
		 	STATUS current
		 	DESCRIPTION
		 		"The eth mode of SyncE status"
		 	::={outputPTPSynceStatusEntry 6}


		-- 1.3.6.1.4.1.43913.16.8.13.4.2
		outputPTPclockStatusTable OBJECT-TYPE
			SYNTAX SEQUENCE OF OutputPTPclockStatusEntry
			MAX-ACCESS not-accessible
			STATUS current
			DESCRIPTION
				"The table of output ptp clock status info."
			::={outputPTPstatus 2}

        -- 1.3.6.1.4.1.43913.16.8.13.4.2.1
		outputPTPclockStatusEntry OBJECT-TYPE
			SYNTAX  OutputPTPclockStatusEntry
			MAX-ACCESS not-accessible
			STATUS current
			DESCRIPTION
				"The entry of output ptp other status info."
			INDEX { outputPTPclockStatusShelfIndex, outputPTPclockStatusSlotIndex }
			::={outputPTPclockStatusTable 1}

		OutputPTPclockStatusEntry ::=
			SEQUENCE{
		       outputPTPclockStatusShelfIndex
		       		Integer32,
		       outputPTPclockStatusSlotIndex
		       		Integer32,
		       outputPTPclockState
		            OutputPTPclockstateType,
		       outputPTPclockCurrentTime
		       		DisplayString,
		       outputPTPclockRunningTime
		       		DisplayString
              }

        -- 1.3.6.1.4.1.43913.16.8.13.4.2.1.1
		outputPTPclockStatusShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPclockStatusEntry 1}

	    -- 1.3.6.1.4.1.43913.16.8.13.4.2.1.2
		outputPTPclockStatusSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={outputPTPclockStatusEntry 2}

		-- 1.3.6.1.4.1.43913.16.8.13.4.2.1.3
		outputPTPclockState OBJECT-TYPE
		 	SYNTAX OutputPTPclockstateType
		 	MAX-ACCESS read-only
		 	STATUS current
		 	DESCRIPTION
		 		"The clock state of ptp output card clock"
		 	::={outputPTPclockStatusEntry 3}

		-- 1.3.6.1.4.1.43913.16.8.13.4.2.1.4
		outputPTPclockCurrentTime OBJECT-TYPE
		 	SYNTAX DisplayString
		 	MAX-ACCESS read-only
		 	STATUS current
		 	DESCRIPTION
		 		"The current time of ptp output card clock"
		 	::={outputPTPclockStatusEntry 4}

		-- 1.3.6.1.4.1.43913.16.8.13.4.2.1.5
		outputPTPclockRunningTime OBJECT-TYPE
		 	SYNTAX DisplayString
		 	MAX-ACCESS read-only
		 	STATUS current
		 	DESCRIPTION
		 		"The running time of ptp output card clock"
		 	::={outputPTPclockStatusEntry 5}


		-- 1.3.6.1.4.1.43913.16.8.13.4.3
		outputPTPStatusTable OBJECT-TYPE
			SYNTAX SEQUENCE OF OutputPTPStatusEntry
			MAX-ACCESS not-accessible
			STATUS current
			DESCRIPTION
				"The table of output ptp status info."
			::={outputPTPstatus 3}

        -- 1.3.6.1.4.1.43913.16.8.13.4.3.1
		outputPTPStatusEntry OBJECT-TYPE
			SYNTAX  OutputPTPStatusEntry
			MAX-ACCESS not-accessible
			STATUS current
			DESCRIPTION
				"The entry of output ptpstatus info."
			INDEX { outputPTPStatusShelfIndex, outputPTPStatusSlotIndex, outputPTPStatusPortIndex }
			::={outputPTPStatusTable 1}

		OutputPTPStatusEntry ::=
			SEQUENCE{
		       outputPTPStatusShelfIndex
		       		Integer32,
		       outputPTPStatusSlotIndex
		       		Integer32,
		       outputPTPStatusPortIndex
		       		Integer32,
		       outputPTPStatusPortEnabled
					DisplayString,
				outputPTPStatusClockID
					DisplayString,
				outputPTPStatusProfile
					DisplayString,
				outputPTPStatusPortState
					DisplayString,
				outputPTPStatusClockClass
					DisplayString,
				outputPTPStatusClockAccuracy
					DisplayString,
				outputPTPStatusTimescale
					DisplayString,
				outputPTPStatusClientNum
					DisplayString,
				outputPTPStatusClientLoad
					DisplayString
              }

        -- 1.3.6.1.4.1.43913.16.8.13.4.3.1.1
		outputPTPStatusShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPStatusEntry 1}

	    -- 1.3.6.1.4.1.43913.16.8.13.4.3.1.1.2
		outputPTPStatusSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={outputPTPStatusEntry 2}

		-- 1.3.6.1.4.1.43913.16.8.13.4.3.1.1.3
		outputPTPStatusPortIndex OBJECT-TYPE
		 	SYNTAX Integer32 (1..4)
		 	MAX-ACCESS not-accessible
		 	STATUS current
		 	DESCRIPTION
		 		"The port index. port1~port4"
		 	::={outputPTPStatusEntry 3 }

		-- 1.3.6.1.4.1.43913.16.8.13.4.3.1.1.4
		outputPTPStatusPortEnabled OBJECT-TYPE
			SYNTAX DisplayString
			MAX-ACCESS read-only
			STATUS current
			DESCRIPTION
				"The PTP port state control flag."
			::= { outputPTPStatusEntry 4 }


		-- 1.3.6.1.4.1.43913.16.8.13.4.3.1.1.5
		outputPTPStatusClockID OBJECT-TYPE
			SYNTAX DisplayString
			MAX-ACCESS read-only
			STATUS current
			DESCRIPTION
				"The clock ID of a PTP port."
			::= { outputPTPStatusEntry 5 }


		-- 1.3.6.1.4.1.43913.16.8.13.4.3.1.1.6
		outputPTPStatusProfile OBJECT-TYPE
			SYNTAX DisplayString
			MAX-ACCESS read-only
			STATUS current
			DESCRIPTION
				"PTP common profile."
			::= { outputPTPStatusEntry 6 }


		-- 1.3.6.1.4.1.43913.16.8.13.4.3.1.1.7
		outputPTPStatusPortState OBJECT-TYPE
			SYNTAX DisplayString
			MAX-ACCESS read-only
			STATUS current
			DESCRIPTION
				"PTP port state."
			::= { outputPTPStatusEntry 7 }


		-- 1.3.6.1.4.1.43913.16.8.13.4.3.1.1.8
		outputPTPStatusClockClass OBJECT-TYPE
			SYNTAX DisplayString
			MAX-ACCESS read-only
			STATUS current
			DESCRIPTION
				"The clock class on a PTP port."
			::= { outputPTPStatusEntry 8 }


		-- 1.3.6.1.4.1.43913.16.8.13.4.3.1.1.9
		outputPTPStatusClockAccuracy OBJECT-TYPE
			SYNTAX DisplayString
			MAX-ACCESS read-only
			STATUS current
			DESCRIPTION
				"The clock accuracy on a PTP port."
			::= { outputPTPStatusEntry 9 }


		-- 1.3.6.1.4.1.43913.16.8.13.4.3.1.1.10
		outputPTPStatusTimescale OBJECT-TYPE
			SYNTAX DisplayString
			MAX-ACCESS read-only
			STATUS current
			DESCRIPTION
				"The timescale on a PTP port."
			::= { outputPTPStatusEntry 10 }


		-- 1.3.6.1.4.1.43913.16.8.13.4.3.1.1.11
		outputPTPStatusClientNum OBJECT-TYPE
			SYNTAX DisplayString
			MAX-ACCESS read-only
			STATUS current
			DESCRIPTION
				"The number of clients on a PTP port."
			::= { outputPTPStatusEntry 11 }


		-- 1.3.6.1.4.1.43913.16.8.13.4.3.1.1.12
		outputPTPStatusClientLoad OBJECT-TYPE
			SYNTAX DisplayString
			MAX-ACCESS read-only
			STATUS current
			DESCRIPTION
				"The percentage of client load on a PTP port."
			::= { outputPTPStatusEntry 12 }


        -- 1.3.6.1.4.1.43913.16.8.13.4.4
		outputPTPNetworkStatusTable OBJECT-TYPE
			SYNTAX SEQUENCE OF OutputPTPNetworkStatusEntry
			MAX-ACCESS not-accessible
			STATUS current
			DESCRIPTION
				"PTP output card network info table."
			::= { outputPTPstatus 4 }


		-- 1.3.6.1.4.1.43913.16.8.13.4.4.1
		outputPTPNetworkStatusEntry OBJECT-TYPE
			SYNTAX OutputPTPNetworkStatusEntry
			MAX-ACCESS not-accessible
			STATUS current
			DESCRIPTION
				"The entry of output PTP network status table."
			INDEX { outputPTPStatusNetworkShelfIndex, outputPTPStatusNetworkSlotIndex }
			::= { outputPTPNetworkStatusTable 1 }


		OutputPTPNetworkStatusEntry ::=
			SEQUENCE {
				outputPTPStatusNetworkShelfIndex
					Integer32,
				outputPTPStatusNetworkSlotIndex
					Integer32,
				outputPTPStatusNetworkEthPortID
					DisplayString,
				outputPTPStatusNetworkHWAddr
					DisplayString
				}


		-- 1.3.6.1.4.1.43913.16.8.13.4.4.1.1
		outputPTPStatusNetworkShelfIndex OBJECT-TYPE
			SYNTAX Integer32  (0..4)
			MAX-ACCESS not-accessible
			STATUS current
			DESCRIPTION
				"The shelf index: main(0), exp1(1), exp2(2), exp3(3), exp4(4)"
			::= { outputPTPNetworkStatusEntry 1 }


		-- 1.3.6.1.4.1.43913.16.8.13.4.4.1.2
		outputPTPStatusNetworkSlotIndex OBJECT-TYPE
			SYNTAX Integer32  (0..14)
			MAX-ACCESS read-only
			STATUS current
			DESCRIPTION
				"The slot index. When the shelf index is 0(main), the slot-index range is 2~9;
		 		 When the shelf index is 1~4(exp1~exp4), the slot-index range is 3~14"
		 	::= { outputPTPNetworkStatusEntry 2 }


		-- 1.3.6.1.4.1.43913.16.8.13.4.4.1.3
		outputPTPStatusNetworkEthPortID OBJECT-TYPE
			SYNTAX DisplayString
			MAX-ACCESS read-only
			STATUS current
			DESCRIPTION
				"IP port ID."
			::= { outputPTPNetworkStatusEntry 3 }


		-- 1.3.6.1.4.1.43913.16.8.13.4.4.1.4
		outputPTPStatusNetworkHWAddr OBJECT-TYPE
			SYNTAX DisplayString
			MAX-ACCESS read-only
			STATUS current
			DESCRIPTION
				"HW address, type and other info of an ethernet port."
			::= { outputPTPNetworkStatusEntry 4 }

		-- 1.3.6.1.4.1.43913.16.8.13.4.5
		outputPTPGeneralStatusTable OBJECT-TYPE
			SYNTAX SEQUENCE OF OutputPTPGeneralStatusEntry
			MAX-ACCESS not-accessible
			STATUS current
			DESCRIPTION
				"PTP output card general status table."
			::= { outputPTPstatus 5 }


		-- 1.3.6.1.4.1.43913.16.8.13.4.5.1
		outputPTPGeneralStatusEntry OBJECT-TYPE
			SYNTAX OutputPTPGeneralStatusEntry
			MAX-ACCESS not-accessible
			STATUS current
			DESCRIPTION
				"The entry of output PTP general status table."
			INDEX { outputPTPGeneralStatusShelfIndex, outputPTPGeneralStatusSlotIndex }
			::= { outputPTPGeneralStatusTable 1 }


		OutputPTPGeneralStatusEntry ::=
			SEQUENCE {
				outputPTPGeneralStatusShelfIndex
					Integer32,
				outputPTPGeneralStatusSlotIndex
					Integer32,
				outputPTPGeneralStatusCPUload
					Integer32,
				outputPTPGeneralStatusMEMload
					Integer32
					  }


		-- 1.3.6.1.4.1.43913.16.8.13.4.5.1.1
		outputPTPGeneralStatusShelfIndex OBJECT-TYPE
			SYNTAX Integer32  (0..4)
			MAX-ACCESS not-accessible
			STATUS current
			DESCRIPTION
				"The shelf index: main(0), exp1(1), exp2(2), exp3(3), exp4(4)"
			::= { outputPTPGeneralStatusEntry 1 }


		-- 1.3.6.1.4.1.43913.16.8.13.4.5.1.2
		outputPTPGeneralStatusSlotIndex OBJECT-TYPE
			SYNTAX Integer32  (0..14)
			MAX-ACCESS read-only
			STATUS current
			DESCRIPTION
				"The slot index. When the shelf index is 0(main), the slot-index range is 2~9;
		 		 When the shelf index is 1~4(exp1~exp4), the slot-index range is 3~14"
		 	::= { outputPTPGeneralStatusEntry 2 }


		-- 1.3.6.1.4.1.43913.16.8.13.4.5.1.3
		outputPTPGeneralStatusCPUload OBJECT-TYPE
			SYNTAX Integer32
			MAX-ACCESS read-only
			STATUS current
			DESCRIPTION
				"PTP output card CPU load percentage."
			::= { outputPTPGeneralStatusEntry 3 }

		-- 1.3.6.1.4.1.43913.16.8.13.4.5.1.4
		outputPTPGeneralStatusMEMload OBJECT-TYPE
			SYNTAX Integer32
			MAX-ACCESS read-only
			STATUS current
			DESCRIPTION
				"PTP output card memory load percentage."
			::= { outputPTPGeneralStatusEntry 4 }


		-- 1.3.6.1.4.1.43913.16.8.13.5
		outputPTPupgrade OBJECT IDENTIFIER ::= { outputPTP 5 }

		-- 1.3.6.1.4.1.43913.16.8.13.5.1
		outputPTPupgradeTable OBJECT-TYPE
			SYNTAX SEQUENCE OF OutputPTPupgradeEntry
			MAX-ACCESS not-accessible
			STATUS current
			DESCRIPTION
				"This table is used to upgrade PTP output card."
			::= { outputPTPupgrade 1 }


		-- 1.3.6.1.4.1.43913.16.8.13.5.1.1
		outputPTPupgradeEntry OBJECT-TYPE
			SYNTAX OutputPTPupgradeEntry
			MAX-ACCESS not-accessible
			STATUS current
			DESCRIPTION
				"The entry of the table."
			INDEX { outputPTPupgradeShelfIndex, outputPTPupgradeSlotIndex }
			::= { outputPTPupgradeTable 1 }


		OutputPTPupgradeEntry ::=
			SEQUENCE {
				outputPTPupgradeShelfIndex
					Integer32,
				outputPTPupgradeSlotIndex
					Integer32,
				outputPTPupgradeCmd
					DisplayString
			 }

		-- 1.3.6.1.4.1.43913.16.8.13.5.1.1.1
		outputPTPupgradeShelfIndex OBJECT-TYPE
			SYNTAX Integer32 (0..4)
			MAX-ACCESS not-accessible
			STATUS current
			DESCRIPTION
				"The shelf index: main(0), exp1(1), exp2(2), exp3(3), exp4(4)."
			::= { outputPTPupgradeEntry 1 }


		-- 1.3.6.1.4.1.43913.16.8.13.5.1.1.2
		outputPTPupgradeSlotIndex OBJECT-TYPE
			SYNTAX Integer32
			MAX-ACCESS read-only
			STATUS current
			DESCRIPTION
				"The slot index. When the index is 0(main), the slot-index range is 2~9;
 				When the  index is 1~4(exp1~exp4), the slot-index range is 3~14."
			::= { outputPTPupgradeEntry 2 }


		-- 1.3.6.1.4.1.43913.16.8.13.5.1.1.3
		outputPTPupgradeCmd OBJECT-TYPE
			SYNTAX DisplayString
			MAX-ACCESS read-write
			STATUS current
			DESCRIPTION
				"The upgrade command, the format should be:file_name,[protocol:]server_ip,user,passwd."
			::= { outputPTPupgradeEntry 3 }


		-- 1.3.6.1.4.1.43913.16.8.13.5.2
		outputPTPupgradeStatusTable OBJECT-TYPE
			SYNTAX SEQUENCE OF OutputPTPupgradeStatusEntry
			MAX-ACCESS not-accessible
			STATUS current
			DESCRIPTION
				"This table is used to get PTP output card upgrade status."
			::= { outputPTPupgrade 2 }


		-- 1.3.6.1.4.1.43913.16.8.13.5.2.1
		outputPTPupgradeStatusEntry OBJECT-TYPE
			SYNTAX OutputPTPupgradeStatusEntry
			MAX-ACCESS not-accessible
			STATUS current
			DESCRIPTION
				"The entry of the table."
			INDEX { outputPTPupgradeStatusShelfIndex, outputPTPupgradeStatusSlotIndex }
			::= { outputPTPupgradeStatusTable 1 }


		OutputPTPupgradeStatusEntry ::=
			SEQUENCE {
				outputPTPupgradeStatusShelfIndex
					Integer32,
				outputPTPupgradeStatusSlotIndex
					Integer32,
				outputPTPupgradeStatus
					UpgradeStatus
			 }

		-- 1.3.6.1.4.1.43913.16.8.13.5.2.1.1
		outputPTPupgradeStatusShelfIndex OBJECT-TYPE
			SYNTAX Integer32
			MAX-ACCESS not-accessible
			STATUS current
			DESCRIPTION
				"The shelf index: main(0), exp1(1), exp2(2), exp3(3), exp4(4)."
			::= { outputPTPupgradeStatusEntry 1 }


		-- 1.3.6.1.4.1.43913.16.8.13.5.2.1.2
		outputPTPupgradeStatusSlotIndex OBJECT-TYPE
			SYNTAX Integer32
			MAX-ACCESS read-only
			STATUS current
			DESCRIPTION
				"The slot index. When the index is 0(main), the slot-index range is 2~9;
 				When the  index is 1~4(exp1~exp4), the slot-index range is 3~14."
			::= { outputPTPupgradeStatusEntry 2 }


		-- 1.3.6.1.4.1.43913.16.8.13.5.2.1.3
		outputPTPupgradeStatus OBJECT-TYPE
			SYNTAX UpgradeStatus
			MAX-ACCESS read-only
			STATUS current
			DESCRIPTION
				"The status of upgrade:
				0--	No upgrade performed since boot up,
				1--	Retrieving file,
				2--	Retrieving file failed,
				3--	Updating flash,
				4--	Updating flash failed,
				5--	Updating package error,
				6--	Upgrade complete.
				"
			::= { outputPTPupgradeStatusEntry 3 }




		-- 1.3.6.1.4.1.43913.16.8.13.6
		outputPTPrxAnnounceMessageTable OBJECT-TYPE
			SYNTAX SEQUENCE OF OutputPTPrxAnnounceMessageEntry
			MAX-ACCESS not-accessible
			STATUS current
			DESCRIPTION
				"This table is used to get PTP output card rx announce message."
			::= { outputPTP 6 }


		-- 1.3.6.1.4.1.43913.16.8.13.6.1
		outputPTPrxAnnounceMessageEntry OBJECT-TYPE
			SYNTAX OutputPTPrxAnnounceMessageEntry
			MAX-ACCESS not-accessible
			STATUS current
			DESCRIPTION
				"The entry of the table."
			INDEX { outputPTPrxAnnounceMessageShelfIndex, outputPTPrxAnnounceMessageSlotIndex, outputPTPrxAnnounceMessagePortIndex }
			::= { outputPTPrxAnnounceMessageTable 1 }


		OutputPTPrxAnnounceMessageEntry ::=
			SEQUENCE {
				outputPTPrxAnnounceMessageShelfIndex
					Integer32,
				outputPTPrxAnnounceMessageSlotIndex
					Integer32,
				outputPTPrxAnnounceMessagePortIndex
					Integer32,
				outputPTPrxAnnounceMessageClockID
					DisplayString,
				outputPTPrxAnnounceMessageClockClass
					Integer32,
				outputPTPrxAnnounceMessageClockAccuracy
					Integer32,
				outputPTPrxAnnounceMessageOffsetScaled
					Integer32,
				outputPTPrxAnnounceMessageOffsetScaledLogVariance
					Integer32,
				outputPTPrxAnnounceMessagePriority1
					Integer32,
				outputPTPrxAnnounceMessagePriority2
					Integer32,
				outputPTPrxAnnounceMessageTimeSource
					Integer32,
				outputPTPrxAnnounceMessageCurrUtcOffset
					Integer32,
				outputPTPrxAnnounceMessageStepsRemoved
					Integer32

			 }

		-- 1.3.6.1.4.1.43913.16.8.13.6.1.1
		outputPTPrxAnnounceMessageShelfIndex OBJECT-TYPE
			SYNTAX Integer32
			MAX-ACCESS read-only
			STATUS current
			DESCRIPTION
				"The shelf index: main(0), exp1(1), exp2(2), exp3(3), exp4(4)."
			::= { outputPTPrxAnnounceMessageEntry 1 }


		-- 1.3.6.1.4.1.43913.16.8.13.6.1.2
		outputPTPrxAnnounceMessageSlotIndex OBJECT-TYPE
			SYNTAX Integer32
			MAX-ACCESS read-only
			STATUS current
			DESCRIPTION
				"The slot index. When the index is 0(main), the slot-index range is 2~9;
 				When the  index is 1~4(exp1~exp4), the slot-index range is 3~14."
			::= { outputPTPrxAnnounceMessageEntry 2 }

		-- 1.3.6.1.4.1.43913.16.8.13.6.1.3
		outputPTPrxAnnounceMessagePortIndex OBJECT-TYPE
			SYNTAX Integer32
			MAX-ACCESS read-only
			STATUS current
			DESCRIPTION
				"The port index."
			::= { outputPTPrxAnnounceMessageEntry 3 }

		-- 1.3.6.1.4.1.43913.16.8.13.6.1.4
		outputPTPrxAnnounceMessageClockID  OBJECT-TYPE
			SYNTAX DisplayString
			MAX-ACCESS read-only
			STATUS current
			DESCRIPTION
				"The clock id."
			::= { outputPTPrxAnnounceMessageEntry 4 }

		-- 1.3.6.1.4.1.43913.16.8.13.6.1.5
		outputPTPrxAnnounceMessageClockClass  OBJECT-TYPE
			SYNTAX Integer32
			MAX-ACCESS read-only
			STATUS current
			DESCRIPTION
				"The ."
			::= { outputPTPrxAnnounceMessageEntry 5 }


		-- 1.3.6.1.4.1.43913.16.8.13.6.1.6
		outputPTPrxAnnounceMessageClockAccuracy  OBJECT-TYPE
			SYNTAX Integer32
			MAX-ACCESS read-only
			STATUS current
			DESCRIPTION
				"The ."
			::= { outputPTPrxAnnounceMessageEntry 6 }


		-- 1.3.6.1.4.1.43913.16.8.13.6.1.7
		outputPTPrxAnnounceMessageOffsetScaled  OBJECT-TYPE
			SYNTAX Integer32
			MAX-ACCESS read-only
			STATUS current
			DESCRIPTION
				"The ."
			::= { outputPTPrxAnnounceMessageEntry 7 }


		-- 1.3.6.1.4.1.43913.16.8.13.6.1.8
		outputPTPrxAnnounceMessageOffsetScaledLogVariance  OBJECT-TYPE
			SYNTAX Integer32
			MAX-ACCESS read-only
			STATUS current
			DESCRIPTION
				"The ."
			::= { outputPTPrxAnnounceMessageEntry 8 }


		-- 1.3.6.1.4.1.43913.16.8.13.6.1.9
		outputPTPrxAnnounceMessagePriority1  OBJECT-TYPE
			SYNTAX Integer32
			MAX-ACCESS read-only
			STATUS current
			DESCRIPTION
				"The ."
			::= { outputPTPrxAnnounceMessageEntry 9 }

		-- 1.3.6.1.4.1.43913.16.8.13.6.1.10
		outputPTPrxAnnounceMessagePriority2  OBJECT-TYPE
			SYNTAX Integer32
			MAX-ACCESS read-only
			STATUS current
			DESCRIPTION
				"The ."
			::= { outputPTPrxAnnounceMessageEntry 10 }

		-- 1.3.6.1.4.1.43913.16.8.13.6.1.11
		outputPTPrxAnnounceMessageTimeSource  OBJECT-TYPE
			SYNTAX Integer32
			MAX-ACCESS read-only
			STATUS current
			DESCRIPTION
				"The ."
			::= { outputPTPrxAnnounceMessageEntry 11 }

		-- 1.3.6.1.4.1.43913.16.8.13.6.1.12
		outputPTPrxAnnounceMessageCurrUtcOffset  OBJECT-TYPE
			SYNTAX Integer32
			MAX-ACCESS read-only
			STATUS current
			DESCRIPTION
				"The ."
			::= { outputPTPrxAnnounceMessageEntry 12 }

		-- 1.3.6.1.4.1.43913.16.8.13.6.1.13
		outputPTPrxAnnounceMessageStepsRemoved  OBJECT-TYPE
			SYNTAX Integer32
			MAX-ACCESS read-only
			STATUS current
			DESCRIPTION
				"The ."
			::= { outputPTPrxAnnounceMessageEntry 13 }




		-- 1.3.6.1.4.1.43913.16.8.13.7
		outputPTPntpBroadcastConfigTable OBJECT-TYPE
			SYNTAX SEQUENCE OF OutputPTPntpBroadcastConfigEntry
			MAX-ACCESS not-accessible
			STATUS current
			DESCRIPTION
				"This table is used to get PTP output card rx announce message."
			::= { outputPTP 7 }


		-- 1.3.6.1.4.1.43913.16.8.13.7.1
		outputPTPntpBroadcastConfigEntry OBJECT-TYPE
			SYNTAX OutputPTPntpBroadcastConfigEntry
			MAX-ACCESS not-accessible
			STATUS current
			DESCRIPTION
				"The entry of the table."
			INDEX { outputPTPntpBroadcastConfigShelfIndex, outputPTPntpBroadcastConfigSlotIndex, outputPTPntpBroadcastConfigPortIndex }
			::= { outputPTPntpBroadcastConfigTable 1 }


		OutputPTPntpBroadcastConfigEntry ::=
			SEQUENCE {
				outputPTPntpBroadcastConfigShelfIndex
					Integer32,
				outputPTPntpBroadcastConfigSlotIndex
					Integer32,
				outputPTPntpBroadcastConfigPortIndex
					Integer32,
				outputPTPntpBroadcastConfigIp
					DisplayString,
				outputPTPntpBroadcastConfigInterval
					Integer32,
				outputPTPntpBroadcastConfigState
					Integer32
			 }

		-- 1.3.6.1.4.1.43913.16.8.13.7.1.1
		outputPTPntpBroadcastConfigShelfIndex OBJECT-TYPE
			SYNTAX Integer32
			MAX-ACCESS read-only
			STATUS current
			DESCRIPTION
				"The shelf index: main(0), exp1(1), exp2(2), exp3(3), exp4(4)."
			::= { outputPTPntpBroadcastConfigEntry 1 }

		-- 1.3.6.1.4.1.43913.16.8.13.7.1.2
		outputPTPntpBroadcastConfigSlotIndex OBJECT-TYPE
			SYNTAX Integer32
			MAX-ACCESS read-only
			STATUS current
			DESCRIPTION
				"The slot index. When the index is 0(main), the slot-index range is 2~9;
				When the  index is 1~4(exp1~exp4), the slot-index range is 3~14"
			::= { outputPTPntpBroadcastConfigEntry 2 }

		-- 1.3.6.1.4.1.43913.16.8.13.7.1.3
		outputPTPntpBroadcastConfigPortIndex OBJECT-TYPE
			SYNTAX Integer32
			MAX-ACCESS read-only
			STATUS current
			DESCRIPTION
				"The ptp out card port index. range 0 ~ 3"
			::= { outputPTPntpBroadcastConfigEntry 3 }

		-- 1.3.6.1.4.1.43913.16.8.13.7.1.4
		outputPTPntpBroadcastConfigIp OBJECT-TYPE
			SYNTAX DisplayString
			MAX-ACCESS read-write
			STATUS current
			DESCRIPTION
				"The ptp out card ntp broadcast ip.
				set format: xxx.xxx.xxx.xxx"
			::= { outputPTPntpBroadcastConfigEntry 4 }

		-- 1.3.6.1.4.1.43913.16.8.13.7.1.5
		outputPTPntpBroadcastConfigInterval OBJECT-TYPE
			SYNTAX Integer32
			MAX-ACCESS read-write
			STATUS current
			DESCRIPTION
				"The ptp out card ntp broadcast interval.
				set format: x
				x : 4 ~ 17"
			::= { outputPTPntpBroadcastConfigEntry 5 }

		-- 1.3.6.1.4.1.43913.16.8.13.7.1.6
		outputPTPntpBroadcastConfigState OBJECT-TYPE
			SYNTAX Integer32
			MAX-ACCESS read-write
			STATUS current
			DESCRIPTION
				"The ptp out card ntp broadcast state.
				set format: x
				x : 0-disable,1-enable"
			::= { outputPTPntpBroadcastConfigEntry 6 }



		-- 1.3.6.1.4.1.43913.16.8.13.8
		outputPTPntpClientMonTable OBJECT-TYPE
			SYNTAX SEQUENCE OF OutputPTPntpClientMonEntry
			MAX-ACCESS not-accessible
			STATUS current
			DESCRIPTION
				"This table is used to get PTP output card ntp client
				mon table."
			::= { outputPTP 8 }


		-- 1.3.6.1.4.1.43913.16.8.13.8.1
		outputPTPntpClientMonEntry OBJECT-TYPE
			SYNTAX OutputPTPntpClientMonEntry
			MAX-ACCESS not-accessible
			STATUS current
			DESCRIPTION
				"The entry of the table."
			INDEX { outputPTPntpClientMonShelfIndex, outputPTPntpClientMonSlotIndex, outputPTPntpClientMonPortIndex,
                    outputPTPntpClientMonIpIndex }
			::= { outputPTPntpClientMonTable 1 }


		OutputPTPntpClientMonEntry ::=
			SEQUENCE {
				outputPTPntpClientMonShelfIndex
					Integer32,
				outputPTPntpClientMonSlotIndex
					Integer32,
				outputPTPntpClientMonPortIndex
					Integer32,
				outputPTPntpClientMonIpIndex
					Integer32,
				outputPTPntpClientMonIp
					DisplayString,
				outputPTPntpClientMonThreshold
					Integer32,
				outputPTPntpClientMonThresholdExceedStatus
					Integer32
			 }

		-- 1.3.6.1.4.1.43913.16.8.13.8.1.1
		outputPTPntpClientMonShelfIndex OBJECT-TYPE
			SYNTAX Integer32
			MAX-ACCESS read-only
			STATUS current
			DESCRIPTION
				"The shelf index: main(0), exp1(1), exp2(2), exp3(3), exp4(4)."
			::= { outputPTPntpClientMonEntry 1 }

		-- 1.3.6.1.4.1.43913.16.8.13.8.1.2
		outputPTPntpClientMonSlotIndex OBJECT-TYPE
			SYNTAX Integer32
			MAX-ACCESS read-only
			STATUS current
			DESCRIPTION
				"The slot index. When the index is 0(main), the slot-index range is 2~9;
				When the  index is 1~4(exp1~exp4), the slot-index range is 3~14."
			::= { outputPTPntpClientMonEntry 2 }

		-- 1.3.6.1.4.1.43913.16.8.13.8.1.3
		outputPTPntpClientMonPortIndex OBJECT-TYPE
			SYNTAX Integer32
			MAX-ACCESS read-only
			STATUS current
			DESCRIPTION
				"The ptp out card port index. range 0 ~ 3"
			::= { outputPTPntpClientMonEntry 3 }

		-- 1.3.6.1.4.1.43913.16.8.13.8.1.4
		outputPTPntpClientMonIpIndex OBJECT-TYPE
			SYNTAX Integer32
			MAX-ACCESS read-only
			STATUS current
			DESCRIPTION
				"The ip index. range 0 ~ 9"
			::= { outputPTPntpClientMonEntry 4 }

		-- 1.3.6.1.4.1.43913.16.8.13.8.1.5
		outputPTPntpClientMonIp OBJECT-TYPE
			SYNTAX DisplayString
			MAX-ACCESS read-write
			STATUS current
			DESCRIPTION
				"Ntp client mon ip.
				set format: xxx.xxx.xxx.xxx"
			::= { outputPTPntpClientMonEntry 5 }

		-- 1.3.6.1.4.1.43913.16.8.13.8.1.6
		outputPTPntpClientMonThreshold OBJECT-TYPE
			SYNTAX Integer32
			MAX-ACCESS read-write
			STATUS current
			DESCRIPTION
				"Ntp client mon threshold.
				set format: x
				x : 0-not mon, 1 ~ 1000000000us"
			::= { outputPTPntpClientMonEntry 6 }

		-- 1.3.6.1.4.1.43913.16.8.13.8.1.7
		outputPTPntpClientMonThresholdExceedStatus OBJECT-TYPE
			SYNTAX Integer32
			MAX-ACCESS read-only
			STATUS current
			DESCRIPTION
				"Ntp client mon threshold exceed status.
				0-not exceed threshold, 1-exceed threshold"
			::= { outputPTPntpClientMonEntry 7 }

        outputPTPntpClientMon OBJECT IDENTIFIER ::= { outputPTP 9 }

		-- 1.3.6.1.4.1.43913.16.8.13.9.1.0
		outputPTPntpClientMonIndex OBJECT-TYPE
			SYNTAX DisplayString
			MAX-ACCESS read-write
			STATUS current
			DESCRIPTION
				"Ntp client mon data get index config.
				set format: a,b,c,d;
				a : shelf index(0~4)
				b : slot index(0~14/3~14)
				c : port index(0~3)
				d : ip index(0~9)"
			::= { outputPTPntpClientMon 1 }

		-- 1.3.6.1.4.1.43913.16.8.13.9.2.0
		outputPTPntpClientMonData OBJECT-TYPE
			SYNTAX DisplayString
			MAX-ACCESS read-only
			STATUS current
			DESCRIPTION
				"Ntp client mon data.
				data total 244 byte,0~3 byte is a unsigned int ipv4 address
				4+(8*i) byte is a long long int value, i(0~29)"
			::= { outputPTPntpClientMon 2 }

		-- 1.3.6.1.4.1.43913.16.8.13.10
		outputPtpIpv6ConfigTable OBJECT-TYPE
			SYNTAX SEQUENCE OF OutputPtpIpv6ConfigEntry
			MAX-ACCESS not-accessible
			STATUS current
			DESCRIPTION
				"The table of output ptp timestamp delay."
			::={outputPTP 10}

        -- 1.3.6.1.4.1.43913.16.8.13.10.1
		outputPtpIpv6ConfigEntry OBJECT-TYPE
			SYNTAX  OutputPtpIpv6ConfigEntry
			MAX-ACCESS not-accessible
			STATUS current
			DESCRIPTION
				"The entry of output ptp timestamp delay."
			INDEX { outputPtpIpv6ConfigShelfIndex, outputPtpIpv6ConfigSlotIndex ,outputPtpIpv6ConfigPortIndex}
			::={outputPtpIpv6ConfigTable 1}

		OutputPtpIpv6ConfigEntry ::=
			SEQUENCE{
		       outputPtpIpv6ConfigShelfIndex
		       		Integer32,
		       outputPtpIpv6ConfigSlotIndex
		       		Integer32,
		       outputPtpIpv6ConfigPortIndex
		       		Integer32,
		       outputPtpIpv6ConfigAddress
		       		DisplayString
              }

        -- 1.3.6.1.4.1.43913.16.8.13.3.11.1.1
		outputPtpIpv6ConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputPtpIpv6ConfigEntry 1}

		-- 1.3.6.1.4.1.43913.16.8.13.3.11.1.2
		outputPtpIpv6ConfigSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPtpIpv6ConfigEntry 2}

		outputPtpIpv6ConfigPortIndex OBJECT-TYPE
		 	SYNTAX Integer32 (0..3)
		 	MAX-ACCESS not-accessible
		 	STATUS current
		 	DESCRIPTION
		 		"The ptp out card port index. range 0 ~ 3"
		 	::={outputPtpIpv6ConfigEntry 3}

		-- 1.3.6.1.4.1.43913.16.8.13.3.11.1.4
		outputPtpIpv6ConfigAddress OBJECT-TYPE
		 	SYNTAX DisplayString
		 	MAX-ACCESS read-write
		 	STATUS current
		 	DESCRIPTION
		 		"Output PTP card ipv6 address.
                format: xxxx:xxxx:xxxx:xxxx:xxxx:xxxx:xxxx:xxxx/xxx"
		 	::={outputPtpIpv6ConfigEntry 4}

		-- 1.3.6.1.4.1.43913.16.8.13.11
		outputPtpAccessControl OBJECT IDENTIFIER ::= { outputPTP 11 }

		-- 1.3.6.1.4.1.43913.16.8.13.11.1
		outputPtpAccessList OBJECT IDENTIFIER ::= { outputPtpAccessControl 1 }

		-- 1.3.6.1.4.1.43913.16.8.13.11.1.1
		outputPTPAclConfigManageTable OBJECT-TYPE
			SYNTAX SEQUENCE OF OutputPTPAclConfigManageEntry
			MAX-ACCESS not-accessible
			STATUS current
			DESCRIPTION
				"The table of output ptp acl config management."
			::={outputPtpAccessList 1}

        -- 1.3.6.1.4.1.43913.16.8.13.11.1.1.1
		outputPTPAclConfigManageEntry OBJECT-TYPE
			SYNTAX  OutputPTPAclConfigManageEntry
			MAX-ACCESS not-accessible
			STATUS current
			DESCRIPTION
				"The entry of output ptp acl config management."
			INDEX { outputPTPAclConfigManageShelfIndex, outputPTPAclConfigManageSlotIndex }
			::={outputPTPAclConfigManageTable 1}

		OutputPTPAclConfigManageEntry ::=
			SEQUENCE{
		       outputPTPAclConfigManageShelfIndex
		       		Integer32,
		       outputPTPAclConfigManageSlotIndex
		       		Integer32,
		       outputPtpGroupLimit
		            Integer32,
		       outputPtpRowLimit
		       		Integer32
              }

        -- 1.3.6.1.4.1.43913.16.8.13.3.5.1.1
		outputPTPAclConfigManageShelfIndex OBJECT-TYPE
		 	SYNTAX Integer32 (0..4)
		 	MAX-ACCESS not-accessible
		 	STATUS current
		 	DESCRIPTION
		 		"The shelf index: main(0), exp1(1), exp2(2), exp3(3), exp4(4)"
		 	::={outputPTPAclConfigManageEntry 1}

	    -- 1.3.6.1.4.1.43913.16.8.13.3.5.1.2
		outputPTPAclConfigManageSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPTPAclConfigManageEntry 2}

		-- 1.3.6.1.4.1.43913.16.8.13.11.1.1
		outputPtpGroupLimit OBJECT-TYPE
			SYNTAX Integer32 (1..100)
			MAX-ACCESS read-write
			STATUS current
			DESCRIPTION
				"Show / Set group-limit ."
			::= { outputPTPAclConfigManageEntry 3}

		-- 1.3.6.1.4.1.43913.16.8.13.11.1.2
		outputPtpRowLimit OBJECT-TYPE
			SYNTAX Integer32 (1..1000)
			MAX-ACCESS read-write
			STATUS current
			DESCRIPTION
				"Show / Set row-limit ."
			::= { outputPTPAclConfigManageEntry 4 }

		-- 1.3.6.1.4.1.43913.16.8.13.11.1.2
		outputPtpAclInfoTable OBJECT-TYPE
			SYNTAX SEQUENCE OF OutputPtpAclInfoEntry
			MAX-ACCESS not-accessible
			STATUS current
			DESCRIPTION
				"The table views the acl-info."
			::= { outputPtpAccessList 2 }

		-- 1.3.6.1.4.1.43913.16.8.13.11.1.2.1
		outputPtpAclInfoEntry OBJECT-TYPE
			SYNTAX OutputPtpAclInfoEntry
			MAX-ACCESS not-accessible
			STATUS current
			DESCRIPTION
				"The entry of acl-info table."
			INDEX { outputPTPAclInfoShelfIndex, outputPTPAclInfoSlotIndex, outputPtpAclInfoIndex }
			::= { outputPtpAclInfoTable 1 }

		OutputPtpAclInfoEntry ::=
			SEQUENCE {
				outputPTPAclInfoShelfIndex
					Integer32,
				outputPTPAclInfoSlotIndex
					Integer32,
				outputPtpAclInfoIndex
					Integer32,
				outputPtpAclNo
					Integer32,
				outputPtpAclRules
					Integer32,
				outputPtpAclType
					DisplayString
			 }
        -- 1.3.6.1.4.1.43913.16.8.13.3.5.1.1
		outputPTPAclInfoShelfIndex OBJECT-TYPE
		 	SYNTAX Integer32 (0..4)
		 	MAX-ACCESS not-accessible
		 	STATUS current
		 	DESCRIPTION
		 		"The shelf index: main(0), exp1(1), exp2(2), exp3(3), exp4(4)"
		 	::={outputPtpAclInfoEntry 1}

	    -- 1.3.6.1.4.1.43913.16.8.13.3.5.1.2
		outputPTPAclInfoSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputPtpAclInfoEntry 2}

		-- 1.3.6.1.4.1.43913.16.8.13.11.1.3.1.1
		outputPtpAclInfoIndex OBJECT-TYPE
			SYNTAX Integer32 (1..20)
			MAX-ACCESS not-accessible
			STATUS current
			DESCRIPTION
				"The index of acl-info table."
			::= { outputPtpAclInfoEntry 3 }

		-- 1.3.6.1.4.1.43913.16.8.13.11.1.3.1.2
		outputPtpAclNo OBJECT-TYPE
			SYNTAX Integer32
			MAX-ACCESS read-only
			STATUS current
			DESCRIPTION
				"The number of group for the acl."
			::= { outputPtpAclInfoEntry 4 }

		-- 1.3.6.1.4.1.43913.16.8.13.11.1.3.1.3
		outputPtpAclRules OBJECT-TYPE
			SYNTAX Integer32
			MAX-ACCESS read-only
			STATUS current
			DESCRIPTION
				"The number of rules for the index."
			::= { outputPtpAclInfoEntry 5 }

		-- 1.3.6.1.4.1.43913.16.8.13.11.1.3.1.4
		outputPtpAclType OBJECT-TYPE
			SYNTAX DisplayString
			MAX-ACCESS read-only
			STATUS current
			DESCRIPTION
				"The type of group for the index. Include ipv4,ipv6 and ethernet."
			::= { outputPtpAclInfoEntry 6 }

		-- 1.3.6.1.4.1.43913.16.8.13.11.1.3
		outputPtpChooseAclNum OBJECT-TYPE
			SYNTAX DisplayString
			MAX-ACCESS read-write
			STATUS current
			DESCRIPTION
				"The value affects the viewing of the outputPtpAclConfigTable.
				set format: a,b,c;
				a : shelf index(0~4)
				b : slot index(0~14/3~14)
				c : acl number(1~100)"
			::= { outputPtpAccessList 3 }

		-- 1.3.6.1.4.1.43913.16.8.13.11.1.4
		outputPtpAclConfigTable OBJECT-TYPE
			SYNTAX SEQUENCE OF OutputPtpAclConfigEntry
			MAX-ACCESS not-accessible
			STATUS current
			DESCRIPTION
				"The table is the access-list configuration of the outputPtpChooseAclNumTable.
				 Please enter the outputPtpChooseAclNumTable before viewing the outputPtpAclConfigTable."
			::= { outputPtpAccessList 4 }

		-- 1.3.6.1.4.1.43913.16.8.13.11.1.6.1
		outputPtpAclConfigEntry OBJECT-TYPE
			SYNTAX OutputPtpAclConfigEntry
			MAX-ACCESS not-accessible
			STATUS current
			DESCRIPTION
				"The entry of acl-Config table."
			INDEX { outputPtpAclConfigIndex }
			::= { outputPtpAclConfigTable 1 }

		OutputPtpAclConfigEntry ::=
			SEQUENCE {
				outputPtpAclConfigIndex
					Integer32,
				outputPtpAclConfigNo
					Integer32,
				outputPtpAclRule
					AclRuleType,
				outputPtpAclProt
					DisplayString,
				outputPtpAclConfigSource
					DisplayString,
				outputPtpAclConfigDest
					DisplayString,
				outputPtpAclConfigOpt
					DisplayString
			 }

		-- 1.3.6.1.4.1.43913.16.8.13.11.1.6.1.1
		outputPtpAclConfigIndex OBJECT-TYPE
			SYNTAX Integer32 (1..20)
			MAX-ACCESS not-accessible
			STATUS current
			DESCRIPTION
				"The index of acl-info table."
			::= { outputPtpAclConfigEntry 1 }


		--  1.3.6.1.4.1.43913.16.8.13.11.1.6.1.2
		outputPtpAclConfigNo OBJECT-TYPE
			SYNTAX Integer32
			MAX-ACCESS read-only
			STATUS current
			DESCRIPTION
				"The acl-number of acl-config table."
			::= { outputPtpAclConfigEntry 2 }


		--  1.3.6.1.4.1.43913.16.8.13.11.1.6.1.3
		outputPtpAclRule OBJECT-TYPE
			SYNTAX AclRuleType
			MAX-ACCESS read-only
			STATUS current
			DESCRIPTION
				"acl rule. The value should be deny and permit."
			::= { outputPtpAclConfigEntry 3 }

		-- 1.3.6.1.4.1.43913.16.8.13.11.1.6.1.4
		outputPtpAclProt OBJECT-TYPE
			SYNTAX DisplayString
			MAX-ACCESS read-only
			STATUS current
			DESCRIPTION
				"acl protocol. The value should be tcp udp and all."
			::= { outputPtpAclConfigEntry 4 }

		-- 1.3.6.1.4.1.43913.16.8.13.11.1.6.1.5
		outputPtpAclConfigSource OBJECT-TYPE
			SYNTAX DisplayString
			MAX-ACCESS read-only
			STATUS current
			DESCRIPTION
				"Source address info. Include ipv4/ipv6."
			::= { outputPtpAclConfigEntry 5 }

		-- 1.3.6.1.4.1.43913.16.8.13.11.1.6.1.6
		outputPtpAclConfigDest OBJECT-TYPE
			SYNTAX DisplayString
			MAX-ACCESS read-only
			STATUS current
			DESCRIPTION
				"Destination address info. Include ipv4/ipv6."
			::= { outputPtpAclConfigEntry 6 }

		-- 1.3.6.1.4.1.43913.16.8.13.11.1.6.1.7
		outputPtpAclConfigOpt OBJECT-TYPE
			SYNTAX DisplayString
			MAX-ACCESS read-only
			STATUS current
			DESCRIPTION
				"Option info .Include the port of protocol, tos, dscp, mac."
			::= { outputPtpAclConfigEntry 7 }

		-- 1.3.6.1.4.1.43913.16.8.13.11.1.5
		outputPtpAclNoClearAll OBJECT-TYPE
			SYNTAX DisplayString
			MAX-ACCESS read-write
			STATUS current
			DESCRIPTION
				"Clear the access-list-number config .Enter the acl-no to be cleared.
				set format: a,b,c;
				a : shelf index(0~4)
				b : slot index(0~14/3~14)
				c : acl number(1~100)"
			::= { outputPtpAccessList 5 }

		-- 1.3.6.1.4.1.43913.16.8.13.11.1.6
		outputPTPaclSettingTable OBJECT-TYPE
			SYNTAX SEQUENCE OF OutputPTPaclSettingEntry
			MAX-ACCESS not-accessible
			STATUS current
			DESCRIPTION
				"This table is used to add or delete a access-list rule."
			::= { outputPtpAccessList 6 }

		-- 1.3.6.1.4.1.43913.16.8.13.11.1.6.1
		outputPTPaclSettingEntry OBJECT-TYPE
			SYNTAX OutputPTPaclSettingEntry
			MAX-ACCESS not-accessible
			STATUS current
			DESCRIPTION
				"The entry of acl-Setting table."
			INDEX { outputPTPaclSettingIndex }
			::= { outputPTPaclSettingTable 1 }

		OutputPTPaclSettingEntry ::=
			SEQUENCE {
				outputPTPaclSettingIndex
					Integer32,
				outputPTPaclSettingNo
					DisplayString,
				outputPTPaclSettingRule
					AclRuleType,
				outputPTPaclSettingEtherType
					AclEtherType,
				outputPTPaclSetting
					DisplayString,
				outputPTPaclSettingCommit
					AclSetType
			 }

		-- 1.3.6.1.4.1.43913.16.8.13.11.1.6.1.1
		outputPTPaclSettingIndex OBJECT-TYPE
			SYNTAX Integer32 (1..1)
			MAX-ACCESS not-accessible
			STATUS current
			DESCRIPTION
				"The index of acl-setting table."
			::= { outputPTPaclSettingEntry 1 }

		-- 1.3.6.1.4.1.43913.16.8.13.11.1.6.1.2
		outputPTPaclSettingNo OBJECT-TYPE
			SYNTAX DisplayString
			MAX-ACCESS read-write
			STATUS current
			DESCRIPTION
				"Acl Number.
				set format: a,b,c;
				a : shelf index(0~4)
				b : slot index(0~14/3~14)
				c : acl number(1~100)"
			::= { outputPTPaclSettingEntry 2 }

		-- 1.3.6.1.4.1.43913.16.8.13.11.1.6.1.3
		outputPTPaclSettingRule OBJECT-TYPE
			SYNTAX AclRuleType
			MAX-ACCESS read-write
			STATUS current
			DESCRIPTION
				"Acl rule. The value should be deny(0) and permit(1)."
			::= { outputPTPaclSettingEntry 3 }

		-- 1.3.6.1.4.1.43913.16.8.13.11.1.6.1.4
		outputPTPaclSettingEtherType OBJECT-TYPE
			SYNTAX AclEtherType
			MAX-ACCESS read-write
			STATUS current
			DESCRIPTION
				"Acl ethertype. The value should be arp(0), ipv4(1), ipv6(2)."
			::= { outputPTPaclSettingEntry 4 }

		-- 1.3.6.1.4.1.43913.16.8.13.11.1.6.1.5
		outputPTPaclSetting OBJECT-TYPE
			SYNTAX DisplayString
			MAX-ACCESS read-write
			STATUS current
			DESCRIPTION
				"The aclSetting. The format is divided into two cases:
				case ipv4: { mac-dest <mac> } | { mac-src <max> } | {icmp} |
					{src {any | <src-addr> netmask <src-netmask>} dest {any | <dest-addr> netmask <dest-netmask>} protocol {tcp|udp}
					source-port {any |<src-port number> <end port>} dest-port {any |<dest-port number> <end port>}
					{tos <tos vaule>|dscp <dscp vaule>}}}
				case ipv6: { mac-dest <mac> } | { mac-src <max> } |
					{src6 {any |<src-ipv6-addr> prefix-length <src-prefix length value>} dest6 {any |<dest-ipv6-addr> prefix-length <dest-
					prefix length value>} protocol {tcp|udp} source-port {any |<src-port number> <end port>} dest-port
					{any |<dest-port number> <end port>} dscp <dscp vaule>}}."
			::= { outputPTPaclSettingEntry 5 }

		-- 1.3.6.1.4.1.43913.16.8.13.11.1.6.1.6
		outputPTPaclSettingCommit OBJECT-TYPE
			SYNTAX AclSetType
			MAX-ACCESS read-write
			STATUS current
			DESCRIPTION
				"commit the acl-setting action. The action should be add(1) and delete(2)"
			::= { outputPTPaclSettingEntry 6 }

		outputPTPptpClientMonStateTable OBJECT-TYPE
			SYNTAX SEQUENCE OF OutputPTPptpClientMonStateEntry
			MAX-ACCESS not-accessible
			STATUS current
			DESCRIPTION
				"This table is used to get PTP output card ptp client
                mon table."
			::= { outputPTP 12 }

		-- 1.3.6.1.4.1.43913.1.8.13.12.1
		outputPTPptpClientMonStateEntry OBJECT-TYPE
			SYNTAX OutputPTPptpClientMonStateEntry
			MAX-ACCESS not-accessible
			STATUS current
			DESCRIPTION
				"The entry of the table."
			INDEX { outputPTPptpClientMonStateShelfIndex, outputPTPptpClientMonStateSlotIndex, outputPTPptpClientMonStatePortIndex }
			::= { outputPTPptpClientMonStateTable 1 }

		OutputPTPptpClientMonStateEntry ::=
			SEQUENCE {
				outputPTPptpClientMonStateShelfIndex
					Integer32,
				outputPTPptpClientMonStateSlotIndex
					Integer32,
				outputPTPptpClientMonStatePortIndex
					Integer32,
				outputPTPptpClientMonState
					Integer32
			 }

		-- 1.3.6.1.4.1.43913.1.8.13.12.1.1
		outputPTPptpClientMonStateShelfIndex OBJECT-TYPE
			SYNTAX Integer32
			MAX-ACCESS read-only
			STATUS current
			DESCRIPTION
				"The shelf index: main(0), exp1(1), exp2(2), exp3(3), exp4(4)."
			::= { outputPTPptpClientMonStateEntry 1 }

		-- 1.3.6.1.4.1.43913.1.8.13.12.1.2
		outputPTPptpClientMonStateSlotIndex OBJECT-TYPE
			SYNTAX Integer32
			MAX-ACCESS read-only
			STATUS current
			DESCRIPTION
				"The slot index. When the index is 0(main), the slot-index range is 2~9;
                When the  index is 1~4(exp1~exp4), the slot-index range is 3~14."
			::= { outputPTPptpClientMonStateEntry 2 }

		-- 1.3.6.1.4.1.43913.1.8.13.12.1.3
		outputPTPptpClientMonStatePortIndex OBJECT-TYPE
			SYNTAX Integer32
			MAX-ACCESS read-only
			STATUS current
			DESCRIPTION
				"The ptp out card port index. range 0 ~ 3"
			::= { outputPTPptpClientMonStateEntry 3 }

		-- 1.3.6.1.4.1.43913.1.8.13.12.1.4
		outputPTPptpClientMonState OBJECT-TYPE
			SYNTAX Integer32
			MAX-ACCESS read-write
			STATUS current
			DESCRIPTION
				"Ptp client mon state.
                disable(0) enable(1)"
			::= { outputPTPptpClientMonStateEntry 4 }


		outputPTPptpClientMonTable OBJECT-TYPE
			SYNTAX SEQUENCE OF OutputPTPptpClientMonEntry
			MAX-ACCESS not-accessible
			STATUS current
			DESCRIPTION
				"This table is used to get PTP output card ptp client
                mon table."
			::= { outputPTP 13 }


		-- 1.3.6.1.4.1.43913.16.8.13.13.1
		outputPTPptpClientMonEntry OBJECT-TYPE
			SYNTAX OutputPTPptpClientMonEntry
			MAX-ACCESS not-accessible
			STATUS current
			DESCRIPTION
				"The entry of the table."
			INDEX { outputPTPptpClientMonShelfIndex, outputPTPptpClientMonSlotIndex, outputPTPptpClientMonPortIndex,
                    outputPTPptpClientMonClockIdIndex }
			::= { outputPTPptpClientMonTable 1 }


		OutputPTPptpClientMonEntry ::=
			SEQUENCE {
				outputPTPptpClientMonShelfIndex
					Integer32,
				outputPTPptpClientMonSlotIndex
					Integer32,
				outputPTPptpClientMonPortIndex
					Integer32,
				outputPTPptpClientMonClockIdIndex
					Integer32,
				outputPTPptpClientMonClockId
					DisplayString,
				outputPTPptpClientMonThreshold
					Integer32,
				outputPTPptpClientMonThresholdExceedStatus
					Integer32
			 }

		-- 1.3.6.1.4.1.43913.16.8.13.13.1.1
		outputPTPptpClientMonShelfIndex OBJECT-TYPE
			SYNTAX Integer32
			MAX-ACCESS read-only
			STATUS current
			DESCRIPTION
				"The shelf index: main(0), exp1(1), exp2(2), exp3(3), exp4(4)."
			::= { outputPTPptpClientMonEntry 1 }

		-- 1.3.6.1.4.1.43913.16.8.13.13.1.2
		outputPTPptpClientMonSlotIndex OBJECT-TYPE
			SYNTAX Integer32
			MAX-ACCESS read-only
			STATUS current
			DESCRIPTION
				"The slot index. When the index is 0(main), the slot-index range is 2~9;
                When the  index is 1~4(exp1~exp4), the slot-index range is 3~14."
			::= { outputPTPptpClientMonEntry 2 }

		-- 1.3.6.1.4.1.43913.16.8.13.13.1.3
		outputPTPptpClientMonPortIndex OBJECT-TYPE
			SYNTAX Integer32
			MAX-ACCESS read-only
			STATUS current
			DESCRIPTION
				"The ptp out card port index. range 0 ~ 3"
			::= { outputPTPptpClientMonEntry 3 }

		-- 1.3.6.1.4.1.43913.16.8.13.13.1.4
		outputPTPptpClientMonClockIdIndex OBJECT-TYPE
			SYNTAX Integer32
			MAX-ACCESS read-only
			STATUS current
			DESCRIPTION
				"The ip index. range 0 ~ 9"
			::= { outputPTPptpClientMonEntry 4 }

		-- 1.3.6.1.4.1.43913.16.8.13.13.1.5
		outputPTPptpClientMonClockId OBJECT-TYPE
			SYNTAX DisplayString
			MAX-ACCESS read-write
			STATUS current
			DESCRIPTION
				"Ptp client mon clock id.
                set format: xx:xx:xx:xx:xx:xx:xx:xx"
			::= { outputPTPptpClientMonEntry 5 }

		-- 1.3.6.1.4.1.43913.16.8.13.13.1.6
		outputPTPptpClientMonThreshold OBJECT-TYPE
			SYNTAX Integer32
			MAX-ACCESS read-write
			STATUS current
			DESCRIPTION
				"Ptp client mon threshold.
                set format: x
                x : 0-not mon, 1 ~ 1000000000ns"
			::= { outputPTPptpClientMonEntry 6 }

		-- 1.3.6.1.4.1.43913.16.8.13.13.1.7
		outputPTPptpClientMonThresholdExceedStatus OBJECT-TYPE
			SYNTAX Integer32
			MAX-ACCESS read-only
			STATUS current
			DESCRIPTION
				"Ptp client mon threshold exceed status.
                0-not exceed threshold, 1-exceed threshold"
			::= { outputPTPptpClientMonEntry 7 }


        outputPTPptpClientMon OBJECT IDENTIFIER ::= { outputPTP 14 }

		-- 1.3.6.1.4.1.43913.1.8.13.14.1.0
		outputPTPptpClientMonIndex OBJECT-TYPE
			SYNTAX DisplayString
			MAX-ACCESS read-write
			STATUS current
			DESCRIPTION
				"Ptp client mon data get index config.
                set format: a,b,c,d;
                a : shelf index(0~4)
                b : slot index(0~14/3~14)
                c : port index(0~3)
                d : clock id index(0~9)"
			::= { outputPTPptpClientMon 1 }

		-- 1.3.6.1.4.1.43913.1.8.13.14.2.0
		outputPTPptpClientMonData OBJECT-TYPE
			SYNTAX DisplayString
			MAX-ACCESS read-only
			STATUS current
			DESCRIPTION
				"Ptp client mon data.
                data total 248 byte,0~7 byte is a char type clock id
                8+(8*i) byte is a double value, i(0~29)"
			::= { outputPTPptpClientMon 2 }

		-- 1.3.6.1.4.1.43913.1.8.13.15
		outputPTPntpClientMonIpv6Table OBJECT-TYPE
			SYNTAX SEQUENCE OF OutputPTPntpClientMonIpv6Entry
			MAX-ACCESS not-accessible
			STATUS current
			DESCRIPTION
				"This table is used to get PTP output card ntp client
                mon table."
			::= { outputPTP 15 }


		-- 1.3.6.1.4.1.43913.1.8.13.15.1
		outputPTPntpClientMonIpv6Entry OBJECT-TYPE
			SYNTAX OutputPTPntpClientMonIpv6Entry
			MAX-ACCESS not-accessible
			STATUS current
			DESCRIPTION
				"The entry of the table."
			INDEX { outputPTPntpClientMonIpv6ShelfIndex, outputPTPntpClientMonIpv6SlotIndex,                        outputPTPntpClientMonIpv6PortIndex,outputPTPntpClientMonIpv6IpIndex }
			::= { outputPTPntpClientMonIpv6Table 1 }


		OutputPTPntpClientMonIpv6Entry ::=
			SEQUENCE {
				outputPTPntpClientMonIpv6ShelfIndex
					Integer32,
				outputPTPntpClientMonIpv6SlotIndex
					Integer32,
				outputPTPntpClientMonIpv6PortIndex
					Integer32,
				outputPTPntpClientMonIpv6IpIndex
					Integer32,
				outputPTPntpClientMonIpv6Addr
					DisplayString,
				outputPTPntpClientMonIpv6Threshold
					Integer32,
				outputPTPntpClientMonIpv6ThresholdExceedStatus
					Integer32
			 }

		-- 1.3.6.1.4.1.43913.1.8.13.15.1.1
		outputPTPntpClientMonIpv6ShelfIndex OBJECT-TYPE
			SYNTAX Integer32
			MAX-ACCESS read-only
			STATUS current
			DESCRIPTION
				"The shelf index: main(0), exp1(1), exp2(2), exp3(3), exp4(4)."
			::= { outputPTPntpClientMonIpv6Entry 1 }

		-- 1.3.6.1.4.1.43913.1.8.13.15.1.2
		outputPTPntpClientMonIpv6SlotIndex OBJECT-TYPE
			SYNTAX Integer32
			MAX-ACCESS read-only
			STATUS current
			DESCRIPTION
				"The slot index. When the index is 0(main), the slot-index range is 2~9;
                When the  index is 1~4(exp1~exp4), the slot-index range is 3~14."
			::= { outputPTPntpClientMonIpv6Entry 2 }

		-- 1.3.6.1.4.1.43913.1.8.13.15.1.3
		outputPTPntpClientMonIpv6PortIndex OBJECT-TYPE
			SYNTAX Integer32
			MAX-ACCESS read-only
			STATUS current
			DESCRIPTION
				"The ptp out card port index. range 0 ~ 3"
			::= { outputPTPntpClientMonIpv6Entry 3 }

		-- 1.3.6.1.4.1.43913.1.8.13.15.1.4
		outputPTPntpClientMonIpv6IpIndex OBJECT-TYPE
			SYNTAX Integer32
			MAX-ACCESS read-only
			STATUS current
			DESCRIPTION
				"The ip index. range 0 ~ 9"
			::= { outputPTPntpClientMonIpv6Entry 4 }

		-- 1.3.6.1.4.1.43913.1.8.13.15.1.5
		outputPTPntpClientMonIpv6Addr OBJECT-TYPE
			SYNTAX DisplayString
			MAX-ACCESS read-write
			STATUS current
			DESCRIPTION
				"Ntp client mon ipv6 address.
                format: xxxx:xxxx:xxxx::xxxx"
			::= { outputPTPntpClientMonIpv6Entry 5 }

		-- 1.3.6.1.4.1.43913.1.8.13.15.1.6
		outputPTPntpClientMonIpv6Threshold OBJECT-TYPE
			SYNTAX Integer32
			MAX-ACCESS read-write
			STATUS current
			DESCRIPTION
				"Ntp client mon threshold.
                set format: x
                x : 0-not mon, 1 ~ 1000000000us"
			::= { outputPTPntpClientMonIpv6Entry 6 }

		-- 1.3.6.1.4.1.43913.1.8.13.15.1.7
		outputPTPntpClientMonIpv6ThresholdExceedStatus OBJECT-TYPE
			SYNTAX Integer32
			MAX-ACCESS read-only
			STATUS current
			DESCRIPTION
				"Ntp client mon threshold exceed status.
                0-not exceed threshold, 1-exceed threshold"
			::= { outputPTPntpClientMonIpv6Entry 7 }


        outputPTPntpClientMonIpv6 OBJECT IDENTIFIER ::= { outputPTP 16 }

		-- 1.3.6.1.4.1.43913.1.8.13.16.1
		outputPTPntpClientMonIpv6Index OBJECT-TYPE
			SYNTAX DisplayString
			MAX-ACCESS read-write
			STATUS current
			DESCRIPTION
				"Ntp client mon data get index config.
                set format: a,b,c,d;
                a : shelf index(0~4)
                b : slot index(0~14/3~14)
                c : port index(0~3)
                d : ip index(0~9)"
			::= { outputPTPntpClientMonIpv6 1 }

		-- 1.3.6.1.4.1.43913.1.8.13.16.2
		outputPTPntpClientMonIpv6Data OBJECT-TYPE
			SYNTAX DisplayString
			MAX-ACCESS read-only
			STATUS current
			DESCRIPTION
				"Ntp client mon data.
                0~15 byte is a unsigned int ipv6 address
                16+(8*i) byte is a long long int value, i(0~29)"
			::= { outputPTPntpClientMonIpv6 2 }


		-- 1.3.6.1.4.1.43913.16.8.13.17
		outputPTPptpClientTable OBJECT-TYPE
			SYNTAX SEQUENCE OF OutputPTPPtpClientEntry
			MAX-ACCESS not-accessible
			STATUS current
			DESCRIPTION
				"The PTP client status table."
			::= { outputPTP 17 }


		-- 1.3.6.1.4.1.43913.16.8.13.17.1
		outputPTPptpClientEntry OBJECT-TYPE
			SYNTAX OutputPTPPtpClientEntry
			MAX-ACCESS not-accessible
			STATUS current
			DESCRIPTION
				"The entry of PTP client table."
			INDEX { ptpClientIndex }
			::= { outputPTPptpClientTable 1 }

		OutputPTPPtpClientEntry ::=
			SEQUENCE {
				ptpClientIndex
					Integer32,
				ptpClientModuleID
					DisplayString,
				ptpClientPortID
					Integer32,
				ptpClientAddr
					DisplayString,
				ptpClientClockID
					DisplayString,
				ptpClientAnnIntv
					Integer32,
				ptpClientSyncIntv
					Integer32,
				ptpClientDelayIntv
					Integer32
			 }

		-- 1.3.6.1.4.1.43913.16.8.13.17.1.1
		ptpClientIndex OBJECT-TYPE
			SYNTAX Integer32 (1..10)
			MAX-ACCESS not-accessible
			STATUS current
			DESCRIPTION
				"PTP client index."
			::= { outputPTPptpClientEntry 1 }


		-- 1.3.6.1.4.1.43913.16.8.13.17.1.2
		ptpClientModuleID OBJECT-TYPE
			SYNTAX DisplayString
			MAX-ACCESS read-write
			STATUS current
			DESCRIPTION
				"set format: a,b;
                a : shelf index(0~4)
                b : slot index(0~14/3~14)."
			::= { outputPTPptpClientEntry 2 }


		-- 1.3.6.1.4.1.43913.16.8.13.17.1.3
		ptpClientPortID OBJECT-TYPE
			SYNTAX Integer32
			MAX-ACCESS read-only
			STATUS current
			DESCRIPTION
				"Module port ID. It should be 1 2 3 4."
			::= { outputPTPptpClientEntry 3 }


		-- 1.3.6.1.4.1.43913.16.8.13.17.1.4
		ptpClientAddr OBJECT-TYPE
			SYNTAX DisplayString
			MAX-ACCESS read-only
			STATUS current
			DESCRIPTION
				"PTP client IP address."
			::= { outputPTPptpClientEntry 4 }


		-- 1.3.6.1.4.1.43913.16.8.13.17.1.5
		ptpClientClockID OBJECT-TYPE
			SYNTAX DisplayString
			MAX-ACCESS read-only
			STATUS current
			DESCRIPTION
				"PTP unicast Clock ID. The valid format should be xx:xx:xx:xx:xx:xx:xx:xx"
			::= { outputPTPptpClientEntry 5 }


		-- 1.3.6.1.4.1.43913.16.8.13.17.1.6
		ptpClientAnnIntv OBJECT-TYPE
			SYNTAX Integer32
			MAX-ACCESS read-only
			STATUS current
			DESCRIPTION
				"PTP client announce interval."
			::= { outputPTPptpClientEntry 6 }


		-- 1.3.6.1.4.1.43913.16.8.13.17.1.7
		ptpClientSyncIntv OBJECT-TYPE
			SYNTAX Integer32
			MAX-ACCESS read-only
			STATUS current
			DESCRIPTION
				"PTP client sync interval."
			::= { outputPTPptpClientEntry 7 }


		-- 1.3.6.1.4.1.43913.16.8.13.17.1.8
		ptpClientDelayIntv OBJECT-TYPE
			SYNTAX Integer32
			MAX-ACCESS read-only
			STATUS current
			DESCRIPTION
				"PTP client delay interval."
			::= { outputPTPptpClientEntry 8 }

		-- 1.3.6.1.4.1.43913.16.8.14
		outputNTP OBJECT IDENTIFIER ::= { inputOutput 14 }

		-- 1.3.6.1.4.1.43913.16.8.14.1
		outputNTPinventoryTable OBJECT-TYPE
			SYNTAX SEQUENCE OF OutputNTPinventoryEntry
			MAX-ACCESS not-accessible
			STATUS current
			DESCRIPTION
				"The table of output NTP card inventory info."
			::= {outputNTP 1}

	    -- 1.3.6.1.4.1.43913.16.8.14.1.1
		outputNTPinventoryEntry OBJECT-TYPE
			SYNTAX  OutputNTPinventoryEntry
			MAX-ACCESS not-accessible
			STATUS current
			DESCRIPTION
				"The entry of output NTP card inventory info."
			INDEX { outputNTPinventoryShelfIndex, outputNTPinventorySlotIndex }
			::= {outputNTPinventoryTable 1}

		OutputNTPinventoryEntry ::=
			SEQUENCE{
				outputNTPinventoryShelfIndex
					Integer32,
				outputNTPinventorySlotIndex
					Integer32,
				outputNTPinventoryPartNum
					DisplayString,
			    outputNTPinventorySerialNum
			    	DisplayString,
			    outputNTPinventoryCLEINum
			    	DisplayString,
			    outputNTPinventoryHwNum
			    	DisplayString,
			    outputNTPinventorySwNum
			    	DisplayString,
			    outputNTPinventoryFPGAVersion
			    	DisplayString,
			    outputNTPinventoryCompatibilityNum
			    	DisplayString
			}

 	    -- 1.3.6.1.4.1.43913.16.8.14.1.1.1
		outputNTPinventoryShelfIndex OBJECT-TYPE
		 	SYNTAX Integer32 (0..4)
		 	MAX-ACCESS not-accessible
		 	STATUS current
		 	DESCRIPTION
		 		"The index: main(0), exp1(1), exp2(2), exp3(3), exp4(4)"
		 	::= {outputNTPinventoryEntry 1}

	    -- 1.3.6.1.4.1.43913.16.8.14.1.1.2
		outputNTPinventorySlotIndex OBJECT-TYPE
		 	SYNTAX Integer32 (0..14)
		 	MAX-ACCESS not-accessible
		 	STATUS current
		 	DESCRIPTION
		 		"The slot index. When the index is 0(main), the slot-index range is 2~9;
		 		 When the index is 1~4(exp1~exp4), the slot-index range is 3~14"
		 	::= {outputNTPinventoryEntry 2}

		-- 1.3.6.1.4.1.43913.16.8.14.1.1.3
		outputNTPinventoryPartNum OBJECT-TYPE
			SYNTAX DisplayString
			MAX-ACCESS read-only
			STATUS current
			DESCRIPTION
				"The part number of output-NTP card"
		    ::= {outputNTPinventoryEntry 3}

		-- 1.3.6.1.4.1.43913.16.8.14.1.1.4
		outputNTPinventorySerialNum OBJECT-TYPE
			SYNTAX DisplayString
			MAX-ACCESS read-only
			STATUS current
			DESCRIPTION
				"The serial number of output-NTP card"
		    ::= {outputNTPinventoryEntry 4}

		-- 1.3.6.1.4.1.43913.16.8.14.1.1.5
		outputNTPinventoryCLEINum OBJECT-TYPE
			SYNTAX DisplayString
			MAX-ACCESS read-only
			STATUS current
			DESCRIPTION
				"The CLEI number of output-NTP card"
		    ::= {outputNTPinventoryEntry 5}

		-- 1.3.6.1.4.1.43913.16.8.14.1.1.6
		outputNTPinventoryHwNum OBJECT-TYPE
			SYNTAX DisplayString
			MAX-ACCESS read-only
			STATUS current
			DESCRIPTION
				"The hardware number of output-NTP card"
		    ::= {outputNTPinventoryEntry 6}

	    -- 1.3.6.1.4.1.43913.16.8.14.1.1.7
		outputNTPinventorySwNum OBJECT-TYPE
			SYNTAX DisplayString
			MAX-ACCESS read-only
			STATUS current
			DESCRIPTION
				"The software number of output-NTP card"
		    ::= {outputNTPinventoryEntry 7}

	   -- 1.3.6.1.4.1.43913.16.8.14.1.1.8
		outputNTPinventoryFPGAVersion OBJECT-TYPE
			SYNTAX DisplayString
			MAX-ACCESS read-only
			STATUS current
			DESCRIPTION
				"The FPGA version of output-NTP card"
		    ::= {outputNTPinventoryEntry 8}

		-- 1.3.6.1.4.1.43913.16.8.14.1.1.9
		outputNTPinventoryCompatibilityNum OBJECT-TYPE
			SYNTAX DisplayString
			MAX-ACCESS read-only
			STATUS current
			DESCRIPTION
				"The compatibility number of output-NTP card"
		    ::= {outputNTPinventoryEntry 9}


		-- 1.3.6.1.4.1.43913.16.8.14.2
		outputNTPimageTable OBJECT-TYPE
			SYNTAX SEQUENCE OF OutputNTPimageEntry
			MAX-ACCESS not-accessible
			STATUS current
			DESCRIPTION
				"The table of output NTP card image info."
			::= {outputNTP 2}

	    -- 1.3.6.1.4.1.43913.16.8.14.2.1
		outputNTPimageEntry OBJECT-TYPE
			SYNTAX  OutputNTPimageEntry
			MAX-ACCESS not-accessible
			STATUS current
			DESCRIPTION
				"The entry of output NTP card image info."
			INDEX { outputNTPimageShelfIndex, outputNTPimageSlotIndex }
			::= {outputNTPimageTable 1}

		OutputNTPimageEntry ::=
			SEQUENCE{
		       outputNTPimageShelfIndex
		       		Integer32,
		       outputNTPimageSlotIndex
		       		Integer32,
			   outputNTPimageActiveImage
			   		Integer32,
			   outputNTPimageActiveVersion
			   		DisplayString,
			   outputNTPimageBackupImage
			   		Integer32,
			   outputNTPimageBackupVersion
			   		DisplayString,
			   outputNTPimageCurrentImage
			   		Integer32,
			   outputNTPchangeActiveStatus
			   		Integer32
			 }

	    -- 1.3.6.1.4.1.43913.16.8.14.2.1.1
		outputNTPimageShelfIndex OBJECT-TYPE
		 	SYNTAX Integer32 (0..4)
		 	MAX-ACCESS not-accessible
		 	STATUS current
		 	DESCRIPTION
		 		"The index: main(0), exp1(1), exp2(2), exp3(3), exp4(4)"
		 	::= {outputNTPimageEntry 1}

	    -- 1.3.6.1.4.1.43913.16.8.14.2.1.2
		outputNTPimageSlotIndex OBJECT-TYPE
		 	SYNTAX Integer32 (0..14)
		 	MAX-ACCESS not-accessible
		 	STATUS current
		 	DESCRIPTION
		 		"The slot index. When the index is 0(main), the slot-index range is 2~9;
		 		 When the index is 1~4(exp1~exp4), the slot-index range is 3~14"
		 	::= {outputNTPimageEntry 2}

		-- 1.3.6.1.4.1.43913.16.8.14.2.1.3
		outputNTPimageActiveImage OBJECT-TYPE
			SYNTAX Integer32
			MAX-ACCESS read-only
			STATUS current
			DESCRIPTION
				"The active image id"
			::= {outputNTPimageEntry 3}

		-- 1.3.6.1.4.1.43913.16.8.14.2.1.4
		outputNTPimageActiveVersion OBJECT-TYPE
			SYNTAX DisplayString
			MAX-ACCESS read-only
			STATUS current
			DESCRIPTION
				"The active image version info"
			::= {outputNTPimageEntry 4}

		-- 1.3.6.1.4.1.43913.16.8.14.2.1.5
		outputNTPimageBackupImage OBJECT-TYPE
			SYNTAX Integer32
			MAX-ACCESS read-only
			STATUS current
			DESCRIPTION
				"The backup image id"
			::= {outputNTPimageEntry 5}

		-- 1.3.6.1.4.1.43913.16.8.14.2.1.6
		outputNTPimageBackupVersion OBJECT-TYPE
			SYNTAX DisplayString
			MAX-ACCESS read-only
			STATUS current
			DESCRIPTION
				"The backup image version info"
			::= {outputNTPimageEntry 6}

		-- 1.3.6.1.4.1.43913.16.8.14.2.1.7
		outputNTPimageCurrentImage OBJECT-TYPE
			SYNTAX Integer32  (1..2)
			MAX-ACCESS read-write
			STATUS current
			DESCRIPTION
				"The current next boot up image id."
			::= {outputNTPimageEntry 7}

		-- 1.3.6.1.4.1.43913.16.8.14.2.1.8
		outputNTPchangeActiveStatus OBJECT-TYPE
			SYNTAX Integer32
			MAX-ACCESS write-only
			STATUS current
			DESCRIPTION
				"Change NTP ouput card active status. Write any value to set."
			::= {outputNTPimageEntry 8}

		-- 1.3.6.1.4.1.43913.16.8.14.3
		outputNTPconfig OBJECT IDENTIFIER ::= { outputNTP 3 }

		-- 1.3.6.1.4.1.43913.16.8.14.3.1
		outputNTPNetworkConfigTable OBJECT-TYPE
			SYNTAX SEQUENCE OF OutputNTPNetworkConfigEntry
			MAX-ACCESS not-accessible
			STATUS current
			DESCRIPTION
				"The table of output NTP card Network config info."
			::= {outputNTPconfig 1}

	    -- 1.3.6.1.4.1.43913.16.8.14.3.1.1
		outputNTPNetworkConfigEntry OBJECT-TYPE
			SYNTAX  OutputNTPNetworkConfigEntry
			MAX-ACCESS not-accessible
			STATUS current
			DESCRIPTION
				"The entry of output NTP card Network config info."
			INDEX { outputNTPNetworkConfigShelfIndex, outputNTPNetworkConfigSlotIndex, outputNTPNetworkConfigPortIndex }
			::= {outputNTPNetworkConfigTable 1}

		OutputNTPNetworkConfigEntry ::=
			SEQUENCE{
		       outputNTPNetworkConfigShelfIndex
		       		Integer32,
		       outputNTPNetworkConfigSlotIndex
		       		Integer32,
		       outputNTPNetworkConfigPortIndex
		            Integer32,
		       outputNTPNetworkConfigIpState
		       		ActionState,
		       outputNTPNetworkConfigIpInfo
		       		DisplayString,
		       outputNTPNetworkConfigVlanMode
		       		ActionState,
		       outputNTPNetworkConfigAutoNegState
		       		ActionState,
		       outputNTPNetworkConfigSpeed
		       		EthLinkSpeedCfg,
		       outputNTPNetworkConfigDuplex
		       		EthlinkDuplexType,
		       outputNTPNetworkConfigIpv6Info
		       		DisplayString
		    }

		-- 1.3.6.1.4.1.43913.16.8.14.3.1.1.1
		outputNTPNetworkConfigShelfIndex OBJECT-TYPE
		 	SYNTAX Integer32 (0..4)
		 	MAX-ACCESS not-accessible
		 	STATUS current
		 	DESCRIPTION
		 		"The shelf index: main(0), exp1(1), exp2(2), exp3(3), exp4(4)"
		 	::= {outputNTPNetworkConfigEntry 1}

	    -- 1.3.6.1.4.1.43913.16.8.14.3.1.1.2
		outputNTPNetworkConfigSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::= {outputNTPNetworkConfigEntry 2}

		-- 1.3.6.1.4.1.43913.16.8.14.3.1.1.3
		outputNTPNetworkConfigPortIndex OBJECT-TYPE
		 	SYNTAX Integer32 (1..4)
		 	MAX-ACCESS not-accessible
		 	STATUS current
		 	DESCRIPTION
		 		"The port index: 1~4"
		 	::= {outputNTPNetworkConfigEntry 3}

		-- 1.3.6.1.4.1.43913.16.8.14.3.1.1.4
		outputNTPNetworkConfigIpState  OBJECT-TYPE
			SYNTAX ActionState
			MAX-ACCESS read-write
			STATUS current
			DESCRIPTION
				"The ip state of output-NTP card port. disable(0), enable(1)"
			::={outputNTPNetworkConfigEntry 4}

		-- 1.3.6.1.4.1.43913.16.8.14.3.1.1.5
		outputNTPNetworkConfigIpInfo  OBJECT-TYPE
			SYNTAX DisplayString
			MAX-ACCESS read-write
			STATUS current
			DESCRIPTION
				"The format is : address,netmask,gateway"
			::={outputNTPNetworkConfigEntry 5}

		-- 1.3.6.1.4.1.43913.16.8.14.3.1.1.6
		outputNTPNetworkConfigVlanMode  OBJECT-TYPE
			SYNTAX ActionState
			MAX-ACCESS read-write
			STATUS current
			DESCRIPTION
				"The vlan mode of output-NTP card port. disable(0), enable(1)"
			::={outputNTPNetworkConfigEntry 6}


		-- 1.3.6.1.4.1.43913.16.8.14.3.1.1.7
		outputNTPNetworkConfigAutoNegState  OBJECT-TYPE
			SYNTAX ActionState
			MAX-ACCESS read-write
			STATUS current
			DESCRIPTION
				"The state of output-NTP card auto negotiation. disable(0), enable(1)"
			::={outputNTPNetworkConfigEntry 7}

		-- 1.3.6.1.4.1.43913.16.8.14.3.1.1.8
		outputNTPNetworkConfigSpeed  OBJECT-TYPE
			SYNTAX EthLinkSpeedCfg
			MAX-ACCESS read-write
			STATUS current
			DESCRIPTION
				"The speed of output-NTP card port. 10M(0), 100M(1), 1000M(2), 10000M(3)"
			::={outputNTPNetworkConfigEntry 8}

		-- 1.3.6.1.4.1.43913.16.8.14.3.1.1.9
		outputNTPNetworkConfigDuplex  OBJECT-TYPE
			SYNTAX EthlinkDuplexType
			MAX-ACCESS read-write
			STATUS current
			DESCRIPTION
				"The duplex type of output-NTP card port. full(0), half(1)"
			::={outputNTPNetworkConfigEntry 9}


		-- 1.3.6.1.4.1.43913.16.8.14.3.1.1.10
		outputNTPNetworkConfigIpv6Info  OBJECT-TYPE
			SYNTAX DisplayString
			MAX-ACCESS read-write
			STATUS current
			DESCRIPTION
				"The ipv6 info of output-NTP card port.
				Read format: ipv6-address,prefix,scope
				Write format: ipv6-address,prefix
				When it is changed, please restart the port to make it effective."
			::={outputNTPNetworkConfigEntry 10}



		 -- 1.3.6.1.4.1.43913.16.8.14.3.5
		outputNTPboardConfigManageTable OBJECT-TYPE
			SYNTAX SEQUENCE OF OutputNTPboardConfigManageEntry
			MAX-ACCESS not-accessible
			STATUS current
			DESCRIPTION
				"The table of output NTP board config management."
			::={outputNTPconfig 2}

        -- 1.3.6.1.4.1.43913.16.8.14.3.2.1
		outputNTPboardConfigManageEntry OBJECT-TYPE
			SYNTAX  OutputNTPboardConfigManageEntry
			MAX-ACCESS not-accessible
			STATUS current
			DESCRIPTION
				"The entry of output NTP board config management."
			INDEX { outputNTPboardConfigManageShelfIndex, outputNTPboardConfigManageSlotIndex }
			::={outputNTPboardConfigManageTable 1}


		OutputNTPboardConfigManageEntry ::=
			SEQUENCE{
		       outputNTPboardConfigManageShelfIndex
		       		Integer32,
		       outputNTPboardConfigManageSlotIndex
		       		Integer32,
		       outputNTPboardConfigManageBackup
		            ActionApply,
		       outputNTPboardConfigManageRestore
		       		Integer32
              }

        -- 1.3.6.1.4.1.43913.16.8.14.3.2.1.1
		outputNTPboardConfigManageShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPboardConfigManageEntry 1}

	    -- 1.3.6.1.4.1.43913.16.8.14.3.2.1.2
		outputNTPboardConfigManageSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPboardConfigManageEntry 2}

        -- 1.3.6.1.4.1.43913.16.8.14.3.2.1.3
        outputNTPboardConfigManageBackup  OBJECT-TYPE
        	SYNTAX   ActionApply
        	MAX-ACCESS write-only
        	STATUS current
        	DESCRIPTION
        		"Backup config of output NTP card locally."
        	::={outputNTPboardConfigManageEntry 3}

        -- 1.3.6.1.4.1.43913.16.8.14.3.2.1.4
        outputNTPboardConfigManageRestore  OBJECT-TYPE
        	SYNTAX   Integer32   (0..1)
        	MAX-ACCESS write-only
        	STATUS current
        	DESCRIPTION
        		"Restore config of output NTP card. 0--dafault config; 1--factory config"
        	::={outputNTPboardConfigManageEntry 4}


       	-- 1.3.6.1.4.1.43913.16.8.13.3.3
		outputNTPntpAuthenticaConfigTable OBJECT-TYPE
			SYNTAX SEQUENCE OF OutputNTPntpAuthenticaConfigEntry
			MAX-ACCESS not-accessible
			STATUS current
			DESCRIPTION
				"The table of output NTP ntp authentica."
			::={outputNTPconfig 3}

        -- 1.3.6.1.4.1.43913.16.8.13.3.3.1
		outputNTPntpAuthenticaConfigEntry OBJECT-TYPE
			SYNTAX  OutputNTPntpAuthenticaConfigEntry
			MAX-ACCESS not-accessible
			STATUS current
			DESCRIPTION
				"The entry of output NTP ntp whitelist."
			INDEX { outputNTPntpAuthenticaConfigShelfIndex, outputNTPntpAuthenticaConfigSlotIndex, outputNTPntpAuthenticaConfigPortIndex }
			::={outputNTPntpAuthenticaConfigTable 1}


		OutputNTPntpAuthenticaConfigEntry ::=
			SEQUENCE{
		       outputNTPntpAuthenticaConfigShelfIndex
		       		Integer32,
		       outputNTPntpAuthenticaConfigSlotIndex
		       		Integer32,
		       outputNTPntpAuthenticaConfigPortIndex
		       		Integer32,
		       outputNTPntpAuthenticaConfigAutokeyState
		       		ActionState,
		       outputNTPntpAuthenticaConfigMD5State
		       		ActionState
              }

        -- 1.3.6.1.4.1.43913.16.8.13.3.3.1.1
		outputNTPntpAuthenticaConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPntpAuthenticaConfigEntry 1}

	    -- 1.3.6.1.4.1.43913.16.8.13.3.3.1.2
		outputNTPntpAuthenticaConfigSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPntpAuthenticaConfigEntry 2}

		-- 1.3.6.1.4.1.43913.16.8.13.3.3.1.3
		outputNTPntpAuthenticaConfigPortIndex OBJECT-TYPE
		 	SYNTAX Integer32 (1..4)
		 	MAX-ACCESS not-accessible
		 	STATUS current
		 	DESCRIPTION
		 		"The port index. "
		 	::={outputNTPntpAuthenticaConfigEntry 3}

        -- 1.3.6.1.4.1.43913.16.8.13.3.3.1.4
        outputNTPntpAuthenticaConfigAutokeyState  OBJECT-TYPE
        	SYNTAX   ActionState
        	MAX-ACCESS read-write
        	STATUS current
        	DESCRIPTION
        		"The state of NTP authentica autokey. enable(1), disable(0)."
        	::={outputNTPntpAuthenticaConfigEntry 4}

       -- 1.3.6.1.4.1.43913.16.8.13.3.3.1.5
        outputNTPntpAuthenticaConfigMD5State  OBJECT-TYPE
        	SYNTAX   ActionState
        	MAX-ACCESS read-write
        	STATUS current
        	DESCRIPTION
        		"The state of NTP authentica MD5. enable(1), disable(0)."
        	::={outputNTPntpAuthenticaConfigEntry 5}



       -- 1.3.6.1.4.1.43913.16.8.13.3.4
		outputNTPntpAuthenticaKeysTable OBJECT-TYPE
			SYNTAX SEQUENCE OF OutputNTPntpAuthenticaKeysEntry
			MAX-ACCESS not-accessible
			STATUS current
			DESCRIPTION
				"The table of output NTP ntp authentica."
			::={outputNTPconfig 4}

        -- 1.3.6.1.4.1.43913.16.8.13.3.4.1
		outputNTPntpAuthenticaKeysEntry OBJECT-TYPE
			SYNTAX  OutputNTPntpAuthenticaKeysEntry
			MAX-ACCESS not-accessible
			STATUS current
			DESCRIPTION
				"The entry of output NTP ntp whitelist."
			INDEX { outputNTPntpAuthenticaKeysShelfIndex, outputNTPntpAuthenticaKeysSlotIndex, outputNTPntpAuthenticaKeysPortIndex }
			::={outputNTPntpAuthenticaKeysTable 1}


		OutputNTPntpAuthenticaKeysEntry ::=
			SEQUENCE{
		       outputNTPntpAuthenticaKeysShelfIndex
		       		Integer32,
		       outputNTPntpAuthenticaKeysSlotIndex
		       		Integer32,
		       outputNTPntpAuthenticaKeysPortIndex
		       		Integer32,
		       outputNTPntpAuthenticaKeysAutokey
		       		DisplayString,
		 	   outputNTPntpAuthenticaKeysMD5key
		       		DisplayString
              }

        -- 1.3.6.1.4.1.43913.16.8.13.3.4.1.1
		outputNTPntpAuthenticaKeysShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPntpAuthenticaKeysEntry 1}

		-- 1.3.6.1.4.1.43913.16.8.13.3.4.1.2
		outputNTPntpAuthenticaKeysSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPntpAuthenticaKeysEntry 2}

		-- 1.3.6.1.4.1.43913.16.8.13.3.4.1.3
		outputNTPntpAuthenticaKeysPortIndex OBJECT-TYPE
		 	SYNTAX Integer32 (1..4)
		 	MAX-ACCESS not-accessible
		 	STATUS current
		 	DESCRIPTION
		 		"The port index."
		 	::={outputNTPntpAuthenticaKeysEntry 3}

       -- 1.3.6.1.4.1.43913.16.8.13.3.4.1.4
        outputNTPntpAuthenticaKeysAutokey  OBJECT-TYPE
        	SYNTAX   DisplayString
        	MAX-ACCESS read-only
        	STATUS current
        	DESCRIPTION
        		"The autokey key value of NTP authentica."
        	::={outputNTPntpAuthenticaKeysEntry 4}

       -- 1.3.6.1.4.1.43913.16.8.13.3.4.1.5
        outputNTPntpAuthenticaKeysMD5key  OBJECT-TYPE
        	SYNTAX   DisplayString
        	MAX-ACCESS read-only
        	STATUS current
        	DESCRIPTION
        		"The MD5 key value of NTP authentica."
        	::={outputNTPntpAuthenticaKeysEntry 5}



       -- 1.3.6.1.4.1.43913.16.8.13.3.5
		outputNTPntplistConfigTable OBJECT-TYPE
			SYNTAX SEQUENCE OF OutputNTPntplistConfigEntry
			MAX-ACCESS not-accessible
			STATUS current
			DESCRIPTION
				"The table of output NTP ntp list state."
			::={outputNTPconfig 5}

        -- 1.3.6.1.4.1.43913.16.8.13.3.5.1
		outputNTPntplistConfigEntry OBJECT-TYPE
			SYNTAX  OutputNTPntplistConfigEntry
			MAX-ACCESS not-accessible
			STATUS current
			DESCRIPTION
				"The entry of output NTP ntp whitelist."
			INDEX { outputNTPntplistConfigShelfIndex, outputNTPntplistConfigSlotIndex, outputNTPntplistConfigPortIndex }
			::={outputNTPntplistConfigTable 1}


		OutputNTPntplistConfigEntry ::=
			SEQUENCE{
		       outputNTPntplistConfigShelfIndex
		       		Integer32,
		       outputNTPntplistConfigSlotIndex
		       		Integer32,
		       outputNTPntplistConfigPortIndex
		       		Integer32,
		       outputNTPntpListState
		       		NtpListState
              }

        -- 1.3.6.1.4.1.43913.16.8.13.3.5.1.1
		outputNTPntplistConfigShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPntplistConfigEntry 1}

	    -- 1.3.6.1.4.1.43913.16.8.13.3.5.1.2
		outputNTPntplistConfigSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPntplistConfigEntry 2}

        -- 1.3.6.1.4.1.43913.16.8.13.3.5.1.3
        outputNTPntplistConfigPortIndex  OBJECT-TYPE
        	SYNTAX   Integer32 (1..4)
        	MAX-ACCESS not-accessible
        	STATUS current
        	DESCRIPTION
        		"The whitelist addr index."
        	::={outputNTPntplistConfigEntry 3}

       -- 1.3.6.1.4.1.43913.16.8.13.3.5.1.4
        outputNTPntpListState  OBJECT-TYPE
        	SYNTAX   NtpListState
        	MAX-ACCESS read-write
        	STATUS current
        	DESCRIPTION
        		"The ntp list state. none(0), whitelist(1), blacklist(2)"
        	::={outputNTPntplistConfigEntry 4}

     	-- 1.3.6.1.4.1.43913.16.8.13.3.6
		outputNTPntpWhitelistTable OBJECT-TYPE
			SYNTAX SEQUENCE OF OutputNTPntpWhitelistEntry
			MAX-ACCESS not-accessible
			STATUS current
			DESCRIPTION
				"The table of output NTP ntp whitelist."
			::={outputNTPconfig 6}

        -- 1.3.6.1.4.1.43913.16.8.13.3.6.1
		outputNTPntpWhitelistEntry OBJECT-TYPE
			SYNTAX  OutputNTPntpWhitelistEntry
			MAX-ACCESS not-accessible
			STATUS current
			DESCRIPTION
				"The entry of output NTP ntp whitelist."
			INDEX { outputNTPntpWhitelistShelfIndex, outputNTPntpWhitelistSlotIndex, outputNTPntpWhitelistPortIndex, outputNTPntpWhitelistIndex }
			::={outputNTPntpWhitelistTable 1}


		OutputNTPntpWhitelistEntry ::=
			SEQUENCE{
		       outputNTPntpWhitelistShelfIndex
		       		Integer32,
		       outputNTPntpWhitelistSlotIndex
		       		Integer32,
		       outputNTPntpWhitelistPortIndex
		       		Integer32,
		       outputNTPntpWhitelistIndex
		       		Integer32,
		       outputNTPntpWhitelistAddr
		       		DisplayString,
		       outputNTPntpWhitelistCount
		       		Integer32,
		       outputNTPntpWhitelistRowStatus
		       		RowStatus
              }

        -- 1.3.6.1.4.1.43913.16.8.13.3.6.1.1
		outputNTPntpWhitelistShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPntpWhitelistEntry 1}

	    -- 1.3.6.1.4.1.43913.16.8.13.3.6.1.2
		outputNTPntpWhitelistSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPntpWhitelistEntry 2}

		-- 1.3.6.1.4.1.43913.16.8.13.3.6.1.3
		outputNTPntpWhitelistPortIndex OBJECT-TYPE
		 	SYNTAX Integer32 (1..4)
		 	MAX-ACCESS not-accessible
		 	STATUS current
		 	DESCRIPTION
		 		"The slot index. "
		 	::={outputNTPntpWhitelistEntry 3}

        -- 1.3.6.1.4.1.43913.16.8.13.3.6.1.4
        outputNTPntpWhitelistIndex  OBJECT-TYPE
        	SYNTAX   Integer32
        	MAX-ACCESS not-accessible
        	STATUS current
        	DESCRIPTION
        		"The whitelist addr index."
        	::={outputNTPntpWhitelistEntry 4}

        -- 1.3.6.1.4.1.43913.16.8.13.3.6.1.5
        outputNTPntpWhitelistAddr  OBJECT-TYPE
        	SYNTAX   DisplayString
        	MAX-ACCESS read-write
        	STATUS current
        	DESCRIPTION
        		"The whitelist addr: xxx.xxx.xxx.xxx or xxx.xxx.xxx.xxx,xxx.xxx.xxx.xxx."
        	::={outputNTPntpWhitelistEntry 5}


         -- 1.3.6.1.4.1.43913.16.8.13.3.6.1.6
        outputNTPntpWhitelistCount  OBJECT-TYPE
        	SYNTAX   Integer32
        	MAX-ACCESS read-only
        	STATUS current
        	DESCRIPTION
        		"The whitelist count."
        	::={outputNTPntpWhitelistEntry 6}

     	-- 1.3.6.1.4.1.43913.16.8.13.3.6.1.7
        outputNTPntpWhitelistRowStatus OBJECT-TYPE
			SYNTAX RowStatus
			MAX-ACCESS read-write
			STATUS current
			DESCRIPTION
				"The row status of NTP whitelist table to control row actions. It has the following actions:

				The status column has six defined values:

				     - `active(1)', which indicates that the conceptual row is
				     available for use by the managed device;

				     - `notInService(2)', which indicates that the conceptual
				     row exists in the agent, but is unavailable for use by
				     the managed device (see NOTE below);

				     - `notReady(3)', which indicates that the conceptual row
				     exists in the agent, but is missing information
				     necessary in order to be available for use by the
				     managed device;

				     - `createAndGo(4)', which is supplied by a management
				     station wishing to create a new instance of a
				     conceptual row and to have its status automatically set
				     to active, making it available for use by the managed
				     device;

				     - `createAndWait(5)', which is supplied by a management
				     station wishing to create a new instance of a
				     conceptual row (but not make it available for use by
				     the managed device); and,

				     - `destroy(6)', which is supplied by a management station
				     wishing to delete all of the instances associated with
				     an existing conceptual row.
				"
			::= { outputNTPntpWhitelistEntry 7 }



		-- 1.3.6.1.4.1.43913.16.8.13.3.7
		outputNTPntpBlacklistTable OBJECT-TYPE
			SYNTAX SEQUENCE OF OutputNTPntpBlacklistEntry
			MAX-ACCESS not-accessible
			STATUS current
			DESCRIPTION
				"The table of output NTP ntp Blacklist."
			::={outputNTPconfig 7}

        -- 1.3.6.1.4.1.43913.16.8.13.3.7.1
		outputNTPntpBlacklistEntry OBJECT-TYPE
			SYNTAX  OutputNTPntpBlacklistEntry
			MAX-ACCESS not-accessible
			STATUS current
			DESCRIPTION
				"The entry of output NTP ntp Blacklist."
			INDEX { outputNTPntpBlacklistShelfIndex, outputNTPntpBlacklistSlotIndex, outputNTPntpBlacklistPortIndex, outputNTPntpBlacklistIndex }
			::={outputNTPntpBlacklistTable 1}


		OutputNTPntpBlacklistEntry ::=
			SEQUENCE{
		       outputNTPntpBlacklistShelfIndex
		       		Integer32,
		       outputNTPntpBlacklistSlotIndex
		       		Integer32,
		       outputNTPntpBlacklistPortIndex
		       		Integer32,
		       outputNTPntpBlacklistIndex
		       		Integer32,
		       outputNTPntpBlacklistAddr
		       		DisplayString,
		       outputNTPntpBlacklistCount
		       		Integer32,
		       outputNTPntpBlacklistRowStatus
		       		RowStatus
              }

        -- 1.3.6.1.4.1.43913.16.8.13.3.7.1.1
		outputNTPntpBlacklistShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPntpBlacklistEntry 1}

	    -- 1.3.6.1.4.1.43913.16.8.13.3.7.1.2
		outputNTPntpBlacklistSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPntpBlacklistEntry 2}

		-- 1.3.6.1.4.1.43913.16.8.13.3.7.1.3
		outputNTPntpBlacklistPortIndex OBJECT-TYPE
		 	SYNTAX Integer32 (1..4)
		 	MAX-ACCESS not-accessible
		 	STATUS current
		 	DESCRIPTION
		 		"The slot index. "
		 	::={outputNTPntpBlacklistEntry 3}

        -- 1.3.6.1.4.1.43913.16.8.13.3.7.1.4
        outputNTPntpBlacklistIndex  OBJECT-TYPE
        	SYNTAX   Integer32
        	MAX-ACCESS not-accessible
        	STATUS current
        	DESCRIPTION
        		"The Blacklist addr index."
        	::={outputNTPntpBlacklistEntry 4}

        -- 1.3.6.1.4.1.43913.16.8.13.3.7.1.5
        outputNTPntpBlacklistAddr  OBJECT-TYPE
        	SYNTAX   DisplayString
        	MAX-ACCESS read-write
        	STATUS current
        	DESCRIPTION
        		"The Blacklist addr : xxx.xxx.xxx.xxx or xxx.xxx.xxx.xxx,xxx.xxx.xxx.xxx"
        	::={outputNTPntpBlacklistEntry 5}

        -- 1.3.6.1.4.1.43913.16.8.13.3.7.1.6
        outputNTPntpBlacklistCount  OBJECT-TYPE
        	SYNTAX   Integer32
        	MAX-ACCESS read-only
        	STATUS current
        	DESCRIPTION
        		"The blacklist count."
        	::={outputNTPntpBlacklistEntry 6}

     	-- 1.3.6.1.4.1.43913.16.8.13.3.7.1.7
        outputNTPntpBlacklistRowStatus OBJECT-TYPE
			SYNTAX RowStatus
			MAX-ACCESS read-write
			STATUS current
			DESCRIPTION
				"The row status of NTP Blacklist table to control row actions. It has the following actions:

				The status column has six defined values:

				     - `active(1)', which indicates that the conceptual row is
				     available for use by the managed device;

				     - `notInService(2)', which indicates that the conceptual
				     row exists in the agent, but is unavailable for use by
				     the managed device (see NOTE below);

				     - `notReady(3)', which indicates that the conceptual row
				     exists in the agent, but is missing information
				     necessary in order to be available for use by the
				     managed device;

				     - `createAndGo(4)', which is supplied by a management
				     station wishing to create a new instance of a
				     conceptual row and to have its status automatically set
				     to active, making it available for use by the managed
				     device;

				     - `createAndWait(5)', which is supplied by a management
				     station wishing to create a new instance of a
				     conceptual row (but not make it available for use by
				     the managed device); and,

				     - `destroy(6)', which is supplied by a management station
				     wishing to delete all of the instances associated with
				     an existing conceptual row.
				"
			::= { outputNTPntpBlacklistEntry 7 }
		-- 1.3.6.1.4.1.43913.16.8.13.3.8
		outputNTPRestartTable OBJECT-TYPE
			SYNTAX SEQUENCE OF OutputNTPRestartEntry
			MAX-ACCESS not-accessible
			STATUS current
			DESCRIPTION
				"The table of output NTP restart action."
			::={outputNTPconfig 8}

        -- 1.3.6.1.4.1.43913.16.8.13.3.8.1
		outputNTPRestartEntry OBJECT-TYPE
			SYNTAX  OutputNTPRestartEntry
			MAX-ACCESS not-accessible
			STATUS current
			DESCRIPTION
				"The entry of output NTP restart action."
			INDEX { outputNTPRestartShelfIndex, outputNTPRestartSlotIndex, outputNTPRestartPortIndex }
			::={outputNTPRestartTable 1}


		OutputNTPRestartEntry ::=
			SEQUENCE{
		       outputNTPRestartShelfIndex
		       		Integer32,
		       outputNTPRestartSlotIndex
		       		Integer32,
		       outputNTPRestartPortIndex
		       		Integer32,
		       outputNTPRestartAction
		       		ActionApply,
		       outputNTPRestartResult
		       		ActionResult
              }

        -- 1.3.6.1.4.1.43913.16.8.13.3.8.1.1
		outputNTPRestartShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPRestartEntry 1}

		-- 1.3.6.1.4.1.43913.16.8.13.3.8.1.2
		outputNTPRestartSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPRestartEntry 2}

		-- 1.3.6.1.4.1.43913.16.8.13.3.8.1.3
		outputNTPRestartPortIndex OBJECT-TYPE
		 	SYNTAX Integer32 (0..4)
		 	MAX-ACCESS not-accessible
		 	STATUS current
		 	DESCRIPTION
		 		"The port index. 0 means the card, 1~4 means the port index"
		 	::={outputNTPRestartEntry 3}

		-- 1.3.6.1.4.1.43913.16.8.13.3.8.1.4
		outputNTPRestartAction OBJECT-TYPE
		 	SYNTAX RebootAction
		 	MAX-ACCESS write-only
		 	STATUS current
		 	DESCRIPTION
		 		" Restart output NTP card"
		 	::={outputNTPRestartEntry 4}

		-- 1.3.6.1.4.1.43913.16.8.13.3.8.1.5
		outputNTPRestartResult OBJECT-TYPE
		 	SYNTAX ActionResult
		 	MAX-ACCESS read-only
		 	STATUS current
		 	DESCRIPTION
		 		" success(1), fail(2)"
		 	::={outputNTPRestartEntry 5}



		-- 1.3.6.1.4.1.43913.16.8.13.3.9
		outputNTPbroadcastTable OBJECT-TYPE
			SYNTAX SEQUENCE OF OutputNTPbroadcastEntry
			MAX-ACCESS not-accessible
			STATUS current
			DESCRIPTION
				"The table of output NTP broadcast config."
			::={outputNTPconfig 9}

        -- 1.3.6.1.4.1.43913.16.8.13.3.9.1
		outputNTPbroadcastEntry OBJECT-TYPE
			SYNTAX  OutputNTPbroadcastEntry
			MAX-ACCESS not-accessible
			STATUS current
			DESCRIPTION
				"The entry of output NTP broadcast action."
			INDEX { outputNTPbroadcastShelfIndex, outputNTPbroadcastSlotIndex, outputNTPbroadcastPortIndex }
			::={outputNTPbroadcastTable 1}


		OutputNTPbroadcastEntry ::=
			SEQUENCE{
		       outputNTPbroadcastShelfIndex
		       		Integer32,
		       outputNTPbroadcastSlotIndex
		       		Integer32,
		       outputNTPbroadcastPortIndex
		       		Integer32,
		       outputNTPbroadcastState
		       		ActionState,
		       outputNTPbroadcastIP
		       		DisplayString,
		       outputNTPbroadcastInterval
		       		Integer32,
		       outputNTPbroadcastConfig
		       		DisplayString
              }

        -- 1.3.6.1.4.1.43913.16.8.13.3.9.1.1
		outputNTPbroadcastShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPbroadcastEntry 1}

		-- 1.3.6.1.4.1.43913.16.8.13.3.9.1.2
		outputNTPbroadcastSlotIndex OBJECT-TYPE
		 	SYNTAX Integer32 (1..14)
		 	MAX-ACCESS not-accessible
		 	STATUS current
		 	DESCRIPTION
		 		"The slot index. When the index is 0(main), the slot-index range is 2~9;
		 		 When the  index is 1~4(exp1~exp4), the slot-index range is 3~14"
		 	::={outputNTPbroadcastEntry 2}

		-- 1.3.6.1.4.1.43913.16.8.13.3.9.1.3
		outputNTPbroadcastPortIndex OBJECT-TYPE
		 	SYNTAX Integer32 (0..4)
		 	MAX-ACCESS not-accessible
		 	STATUS current
		 	DESCRIPTION
		 		"The port index. 0 means the card, 1~4 means the port index"
		 	::={outputNTPbroadcastEntry 3}

		-- 1.3.6.1.4.1.43913.16.8.13.3.9.1.4
		outputNTPbroadcastState OBJECT-TYPE
		 	SYNTAX ActionApply
		 	MAX-ACCESS write-only
		 	STATUS current
		 	DESCRIPTION
		 		" enable(1), disable(0)"
		 	::={outputNTPbroadcastEntry 4}

		-- 1.3.6.1.4.1.43913.16.8.13.3.9.1.5
		outputNTPbroadcastIP OBJECT-TYPE
		 	SYNTAX DisplayString
		 	MAX-ACCESS write-only
		 	STATUS current
		 	DESCRIPTION
		 		"Broadcast ip address"
		 	::={outputNTPbroadcastEntry 5}

		-- 1.3.6.1.4.1.43913.16.8.13.3.9.1.6
		outputNTPbroadcastInterval OBJECT-TYPE
		 	SYNTAX Integer32
		 	MAX-ACCESS write-only
		 	STATUS current
		 	DESCRIPTION
		 		"Broadcast interval 3~17"
		 	::={outputNTPbroadcastEntry 6}

		-- 1.3.6.1.4.1.43913.16.8.13.3.9.1.7
		outputNTPbroadcastConfig OBJECT-TYPE
		 	SYNTAX DisplayString
		 	MAX-ACCESS read-only
		 	STATUS current
		 	DESCRIPTION
		 		"Broadcast config: state;ipaddr;interval;"
		 	::={outputNTPbroadcastEntry 7}


		-- 1.3.6.1.4.1.43913.16.8.14.4
		outputNTPstatus OBJECT IDENTIFIER ::= { outputNTP 4 }

		-- 1.3.6.1.4.1.43913.16.8.14.4.1
		outputNTPclockStatusTable OBJECT-TYPE
			SYNTAX SEQUENCE OF OutputNTPclockStatusEntry
			MAX-ACCESS not-accessible
			STATUS current
			DESCRIPTION
				"The table of output NTP clock status info."
			::={outputNTPstatus 1}

        -- 1.3.6.1.4.1.43913.16.8.14.4.1.1
		outputNTPclockStatusEntry OBJECT-TYPE
			SYNTAX  OutputNTPclockStatusEntry
			MAX-ACCESS not-accessible
			STATUS current
			DESCRIPTION
				"The entry of output NTP other status info."
			INDEX { outputNTPclockStatusShelfIndex, outputNTPclockStatusSlotIndex }
			::={outputNTPclockStatusTable 1}

		OutputNTPclockStatusEntry ::=
			SEQUENCE{
		       outputNTPclockStatusShelfIndex
		       		Integer32,
		       outputNTPclockStatusSlotIndex
		       		Integer32,
		       outputNTPclockState
		            OutputPTPclockstateType,
		       outputNTPclockCurrentTime
		       		DisplayString,
		       outputNTPclockRunningTime
		       		DisplayString
              }

        -- 1.3.6.1.4.1.43913.16.8.14.4.1.1.1
		outputNTPclockStatusShelfIndex OBJECT-TYPE
		 	SYNTAX Integer32 (0..4)
		 	MAX-ACCESS not-accessible
		 	STATUS current
		 	DESCRIPTION
		 		"The shelf index: main(0), exp1(1), exp2(2), exp3(3), exp4(4)"
		 	::={outputNTPclockStatusEntry 1}

	    -- 1.3.6.1.4.1.43913.16.8.14.4.1.1.2
		outputNTPclockStatusSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={outputNTPclockStatusEntry 2}

		-- 1.3.6.1.4.1.43913.16.8.14.4.1.1.3
		outputNTPclockState OBJECT-TYPE
		 	SYNTAX OutputPTPclockstateType
		 	MAX-ACCESS read-only
		 	STATUS current
		 	DESCRIPTION
		 		"The clock state of NTP output card clock"
		 	::={outputNTPclockStatusEntry 3}

		-- 1.3.6.1.4.1.43913.16.8.14.4.1.1.4
		outputNTPclockCurrentTime OBJECT-TYPE
		 	SYNTAX DisplayString
		 	MAX-ACCESS read-only
		 	STATUS current
		 	DESCRIPTION
		 		"The current time of NTP output card clock"
		 	::={outputNTPclockStatusEntry 4}

		-- 1.3.6.1.4.1.43913.16.8.14.4.1.1.5
		outputNTPclockRunningTime OBJECT-TYPE
		 	SYNTAX DisplayString
		 	MAX-ACCESS read-only
		 	STATUS current
		 	DESCRIPTION
		 		"The running time of NTP output card clock"
		 	::={outputNTPclockStatusEntry 5}



		 		-- 1.3.6.1.4.1.43913.16.8.13.4.2
		outputNTPNetworkStatusTable OBJECT-TYPE
			SYNTAX SEQUENCE OF OutputNTPNetworkStatusEntry
			MAX-ACCESS not-accessible
			STATUS current
			DESCRIPTION
				"NTP output card network info table."
			::= { outputNTPstatus 2 }


		-- 1.3.6.1.4.1.43913.16.8.13.4.2.1
		outputNTPNetworkStatusEntry OBJECT-TYPE
			SYNTAX OutputNTPNetworkStatusEntry
			MAX-ACCESS not-accessible
			STATUS current
			DESCRIPTION
				"The entry of output NTP network status table."
			INDEX { outputNTPStatusNetworkShelfIndex, outputNTPStatusNetworkSlotIndex }
			::= { outputNTPNetworkStatusTable 1 }


		OutputNTPNetworkStatusEntry ::=
			SEQUENCE {
				outputNTPStatusNetworkShelfIndex
					Integer32,
				outputNTPStatusNetworkSlotIndex
					Integer32,
				outputNTPStatusNetworkEthPortID
					DisplayString,
				outputNTPStatusNetworkHWAddr
					DisplayString
				}


		-- 1.3.6.1.4.1.43913.16.8.13.4.2.1.1
		outputNTPStatusNetworkShelfIndex OBJECT-TYPE
			SYNTAX Integer32  (0..4)
			MAX-ACCESS not-accessible
			STATUS current
			DESCRIPTION
				"The shelf index: main(0), exp1(1), exp2(2), exp3(3), exp4(4)"
			::= { outputNTPNetworkStatusEntry 1 }


		-- 1.3.6.1.4.1.43913.16.8.13.4.2.1.2
		outputNTPStatusNetworkSlotIndex OBJECT-TYPE
			SYNTAX Integer32  (0..14)
			MAX-ACCESS read-only
			STATUS current
			DESCRIPTION
				"The slot index. When the shelf index is 0(main), the slot-index range is 2~9;
		 		 When the shelf index is 1~4(exp1~exp4), the slot-index range is 3~14"
		 	::= { outputNTPNetworkStatusEntry 2 }


		-- 1.3.6.1.4.1.43913.16.8.13.4.2.1.3
		outputNTPStatusNetworkEthPortID OBJECT-TYPE
			SYNTAX DisplayString
			MAX-ACCESS read-only
			STATUS current
			DESCRIPTION
				"IP port ID."
			::= { outputNTPNetworkStatusEntry 3 }


		-- 1.3.6.1.4.1.43913.16.8.13.4.2.1.4
		outputNTPStatusNetworkHWAddr OBJECT-TYPE
			SYNTAX DisplayString
			MAX-ACCESS read-only
			STATUS current
			DESCRIPTION
				"HW address, type and other info of an ethernet port."
			::= { outputNTPNetworkStatusEntry 4 }

		-- 1.3.6.1.4.1.43913.16.8.13.4.3
		outputNTPGeneralStatusTable OBJECT-TYPE
			SYNTAX SEQUENCE OF OutputNTPGeneralStatusEntry
			MAX-ACCESS not-accessible
			STATUS current
			DESCRIPTION
				"NTP output card general status table."
			::= { outputNTPstatus 3 }


		-- 1.3.6.1.4.1.43913.16.8.13.4.3.1
		outputNTPGeneralStatusEntry OBJECT-TYPE
			SYNTAX OutputNTPGeneralStatusEntry
			MAX-ACCESS not-accessible
			STATUS current
			DESCRIPTION
				"The entry of output NTP general status table."
			INDEX { outputNTPGeneralStatusShelfIndex, outputNTPGeneralStatusSlotIndex }
			::= { outputNTPGeneralStatusTable 1 }


		OutputNTPGeneralStatusEntry ::=
			SEQUENCE {
				outputNTPGeneralStatusShelfIndex
					Integer32,
				outputNTPGeneralStatusSlotIndex
					Integer32,
				outputNTPGeneralStatusCPUload
					Integer32,
				outputNTPGeneralStatusMEMload
					Integer32
					  }


		-- 1.3.6.1.4.1.43913.16.8.13.4.3.1.1
		outputNTPGeneralStatusShelfIndex OBJECT-TYPE
			SYNTAX Integer32  (0..4)
			MAX-ACCESS not-accessible
			STATUS current
			DESCRIPTION
				"The shelf index: main(0), exp1(1), exp2(2), exp3(3), exp4(4)"
			::= { outputNTPGeneralStatusEntry 1 }


		-- 1.3.6.1.4.1.43913.16.8.13.4.3.1.2
		outputNTPGeneralStatusSlotIndex OBJECT-TYPE
			SYNTAX Integer32  (0..14)
			MAX-ACCESS read-only
			STATUS current
			DESCRIPTION
				"The slot index. When the shelf index is 0(main), the slot-index range is 2~9;
		 		 When the shelf index is 1~4(exp1~exp4), the slot-index range is 3~14"
		 	::= { outputNTPGeneralStatusEntry 2 }


		-- 1.3.6.1.4.1.43913.16.8.13.4.3.1.3
		outputNTPGeneralStatusCPUload OBJECT-TYPE
			SYNTAX Integer32
			MAX-ACCESS read-only
			STATUS current
			DESCRIPTION
				"NTP output card CPU load percentage."
			::= { outputNTPGeneralStatusEntry 3 }

		-- 1.3.6.1.4.1.43913.16.8.13.4.3.1.4
		outputNTPGeneralStatusMEMload OBJECT-TYPE
			SYNTAX Integer32
			MAX-ACCESS read-only
			STATUS current
			DESCRIPTION
				"NTP output card memory load percentage."
			::= { outputNTPGeneralStatusEntry 4 }



		-- 1.3.6.1.4.1.43913.16.8.14.5
		outputNTPupgrade OBJECT IDENTIFIER ::= { outputNTP 5 }

		-- 1.3.6.1.4.1.43913.16.8.13.5.1
		outputNTPupgradeTable OBJECT-TYPE
			SYNTAX SEQUENCE OF OutputNTPupgradeEntry
			MAX-ACCESS not-accessible
			STATUS current
			DESCRIPTION
				"This table is used to upgrade NTP output card."
			::= { outputNTPupgrade 1 }


		-- 1.3.6.1.4.1.43913.16.8.13.5.1.1
		outputNTPupgradeEntry OBJECT-TYPE
			SYNTAX OutputNTPupgradeEntry
			MAX-ACCESS not-accessible
			STATUS current
			DESCRIPTION
				"The entry of the table."
			INDEX { outputNTPupgradeShelfIndex, outputNTPupgradeSlotIndex }
			::= { outputNTPupgradeTable 1 }


		OutputNTPupgradeEntry ::=
			SEQUENCE {
				outputNTPupgradeShelfIndex
					Integer32,
				outputNTPupgradeSlotIndex
					Integer32,
				outputNTPupgradeCmd
					DisplayString
			 }

		-- 1.3.6.1.4.1.43913.16.8.13.5.1.1.1
		outputNTPupgradeShelfIndex OBJECT-TYPE
			SYNTAX Integer32 (0..4)
			MAX-ACCESS not-accessible
			STATUS current
			DESCRIPTION
				"The shelf index: main(0), exp1(1), exp2(2), exp3(3), exp4(4)."
			::= { outputNTPupgradeEntry 1 }


		-- 1.3.6.1.4.1.43913.16.8.13.5.1.1.2
		outputNTPupgradeSlotIndex OBJECT-TYPE
			SYNTAX Integer32
			MAX-ACCESS read-only
			STATUS current
			DESCRIPTION
				"The slot index. When the index is 0(main), the slot-index range is 2~9;
 				When the  index is 1~4(exp1~exp4), the slot-index range is 3~14."
			::= { outputNTPupgradeEntry 2 }


		-- 1.3.6.1.4.1.43913.16.8.13.5.1.1.3
		outputNTPupgradeCmd OBJECT-TYPE
			SYNTAX DisplayString
			MAX-ACCESS read-write
			STATUS current
			DESCRIPTION
				"The upgrade command, the format should be:file_name,[protocol:]server_ip,user,passwd."
			::= { outputNTPupgradeEntry 3 }


		-- 1.3.6.1.4.1.43913.16.8.13.5.2
		outputNTPupgradeStatusTable OBJECT-TYPE
			SYNTAX SEQUENCE OF OutputNTPupgradeStatusEntry
			MAX-ACCESS not-accessible
			STATUS current
			DESCRIPTION
				"This table is used to get NTP output card upgrade status."
			::= { outputNTPupgrade 2 }


		-- 1.3.6.1.4.1.43913.16.8.13.5.2.1
		outputNTPupgradeStatusEntry OBJECT-TYPE
			SYNTAX OutputNTPupgradeStatusEntry
			MAX-ACCESS not-accessible
			STATUS current
			DESCRIPTION
				"The entry of the table."
			INDEX { outputNTPupgradeStatusShelfIndex, outputNTPupgradeStatusSlotIndex }
			::= { outputNTPupgradeStatusTable 1 }


		OutputNTPupgradeStatusEntry ::=
			SEQUENCE {
				outputNTPupgradeStatusShelfIndex
					Integer32,
				outputNTPupgradeStatusSlotIndex
					Integer32,
				outputNTPupgradeStatus
					UpgradeStatus
			 }

		-- 1.3.6.1.4.1.43913.16.8.13.5.2.1.1
		outputNTPupgradeStatusShelfIndex OBJECT-TYPE
			SYNTAX Integer32
			MAX-ACCESS not-accessible
			STATUS current
			DESCRIPTION
				"The shelf index: main(0), exp1(1), exp2(2), exp3(3), exp4(4)."
			::= { outputNTPupgradeStatusEntry 1 }


		-- 1.3.6.1.4.1.43913.16.8.13.5.2.1.2
		outputNTPupgradeStatusSlotIndex OBJECT-TYPE
			SYNTAX Integer32
			MAX-ACCESS read-only
			STATUS current
			DESCRIPTION
				"The slot index. When the index is 0(main), the slot-index range is 2~9;
 				When the  index is 1~4(exp1~exp4), the slot-index range is 3~14."
			::= { outputNTPupgradeStatusEntry 2 }


		-- 1.3.6.1.4.1.43913.16.8.13.5.2.1.3
		outputNTPupgradeStatus OBJECT-TYPE
			SYNTAX UpgradeStatus
			MAX-ACCESS read-only
			STATUS current
			DESCRIPTION
				"The status of upgrade:
				0--	No upgrade performed since boot up,
				1--	Retrieving file,
				2--	Retrieving file failed,
				3--	Updating flash,
				4--	Updating flash failed,
				5--	Updating package error,
				6--	Upgrade complete.
				"
			::= { outputNTPupgradeStatusEntry 3 }



		-- 1.3.6.1.4.1.43913.16.8.15
		outputFreqGenerationTable OBJECT-TYPE
			SYNTAX SEQUENCE OF OutputFreqGenerationEntry
			MAX-ACCESS not-accessible
			STATUS current
			DESCRIPTION
				"The output-freq card generation configration table."
			::= { inputOutput 15 }


		-- 1.3.6.1.4.1.43913.16.8.15.1
		outputFreqGenerationEntry OBJECT-TYPE
			SYNTAX OutputFreqGenerationEntry
			MAX-ACCESS not-accessible
			STATUS current
			DESCRIPTION
				"The entry of output-freq card generation configration table."
			INDEX { outFreqGenerationIndex, outFreqSlot}
			::= { outputFreqGenerationTable 1 }


		OutputFreqGenerationEntry ::=
			SEQUENCE {
				outFreqGenerationIndex
					Integer32,
				outFreqSlot
					Integer32,
				outFreqWarmup
					OutputControlFreq,
				outFreqFreerun
					OutputControlFreq,
				outFreqHoldover
					OutputControlFreq,
				outFreqFasttrack
					OutputControlFreq
			 }

		-- 1.3.6.1.4.1.43913.16.8.15.1.1
		outFreqGenerationIndex OBJECT-TYPE
			SYNTAX Integer32 (0..4)
			MAX-ACCESS not-accessible
			STATUS current
			DESCRIPTION
				"The index of output-freq card generation configration table."
			::= { outputFreqGenerationEntry 1 }


		-- 1.3.6.1.4.1.43913.16.8.15.1.2
		outFreqSlot OBJECT-TYPE
			SYNTAX Integer32 (1..14)
			MAX-ACCESS read-only
			STATUS current
			DESCRIPTION
				"The slot number of output-freq card. The range is 1~9."
			::= { outputFreqGenerationEntry 2 }


		-- 1.3.6.1.4.1.43913.16.8.15.1.3
		outFreqWarmup OBJECT-TYPE
			SYNTAX OutputControlFreq
			MAX-ACCESS read-write
			STATUS current
			DESCRIPTION
				"The warmup configration of output-freq card.
				The value is off(0), on(1)."
			::= { outputFreqGenerationEntry 3 }


		-- 1.3.6.1.4.1.43913.16.8.15.1.4
		outFreqFreerun OBJECT-TYPE
			SYNTAX OutputControlFreq
			MAX-ACCESS read-write
			STATUS current
			DESCRIPTION
				"The freerun configration of output-freq card.
				The value is off(0), on(1)."
			::= { outputFreqGenerationEntry 4 }


		-- 1.3.6.1.4.1.43913.16.8.15.1.5
		outFreqHoldover OBJECT-TYPE
			SYNTAX OutputControlFreq
			MAX-ACCESS read-write
			STATUS current
			DESCRIPTION
				"The holdover configration of output-freq card.
				The value is off(0), on(1)."
			::= { outputFreqGenerationEntry 5 }


		-- 1.3.6.1.4.1.43913.16.8.15.1.6
		outFreqFasttrack OBJECT-TYPE
			SYNTAX OutputControlFreq
			MAX-ACCESS read-write
			STATUS current
			DESCRIPTION
				"The fasttrack configration of output-freq card.
				The value is off(0), on(1)."
			::= { outputFreqGenerationEntry 6 }







		-- 1.3.6.1.4.1.43913.16.8.20
		sm2000TrapOutputRedundancy NOTIFICATION-TYPE
			OBJECTS { outRedundancyIndex, outputRedundancySlot, outputRedundancyState }
			STATUS current
			DESCRIPTION
				"SM2000-5G output redundancy configuration trap object which specifies shelf ID, slot ID and state."
			::= { inputOutput 20 }

		-- 1.3.6.1.4.1.43913.16.8.21
		sm2000TrapOutputE1Generation NOTIFICATION-TYPE
			OBJECTS { outE1GenerationIndex, outE1Slot, outE1Warmup, outE1Freerun, outE1Holdover, outE1Fasttrack }
			STATUS current
			DESCRIPTION
				"SM2000-5G output E1 generation configuration trap object which specifies shelf ID, slot ID, warm up, free run, hold over and fast track state."
			::= { inputOutput 21 }


		-- 1.3.6.1.4.1.43913.16.8.22
		sm2000TrapOutputPPSTod NOTIFICATION-TYPE
			OBJECTS { outputPPSTodIndex, outputPPSTodSlotIndex, outputPPSTodState }
			STATUS current
			DESCRIPTION
				"SM2000-5G output PPS-TOD configuration trap object which specifies shelf ID, slot ID and state."
			::= { inputOutput 22 }


		-- 1.3.6.1.4.1.43913.16.8.23
		sm2000TrapOutputIRIG NOTIFICATION-TYPE
			OBJECTS { outputIRIGIndex, outputIRIGSlotIndex, outputIRIGState }
			STATUS current
			DESCRIPTION
				"SM2000-5G output IRIG configuration trap object which specifies shelf ID, slot ID and state."
			::= { inputOutput 23 }


		-- 1.3.6.1.4.1.43913.16.8.24
		sm2000TrapOutputPPS NOTIFICATION-TYPE
			OBJECTS { outputPPSState, outputPPSGenWarmup, outputPPSGenFreerun, outputPPSGenHoldover, outputPPSGenFasttrack }
			STATUS current
			DESCRIPTION
				"SM2000-5G output PPS configuration trap object which specifies PPS state, generation warm up, generation free run, generation hold over, generation fast track."
			::= { inputOutput 24 }


		-- 1.3.6.1.4.1.43913.16.8.25
		sm2000TrapOutput10M NOTIFICATION-TYPE
			OBJECTS { output10MState, output10MGenWarmup, output10MGenFreerun, output10MGenHoldover, output10MGenFasttrack }
			STATUS current
			DESCRIPTION
				"SM2000-5G output PPS configuration trap object which specifies 10M state, generation warm up, generation free run, generation hold over, generation fast track."
			::= { inputOutput 25 }



		-- 1.3.6.1.4.1.43913.16.8.26
		sm2000TrapOutputCard NOTIFICATION-TYPE
			OBJECTS { outputCardIndex, outputCardSlotID, outputCardState, outputCardE1Signal }
			STATUS current
			DESCRIPTION
				"SM2000-5G output card configuration trap object whick specifies ouput card state, E1 signal"
			::={ inputOutput 26 }

	    -- 1.3.6.1.4.1.43913.16.8.27
		sm2000TrapOutputPTPimage NOTIFICATION-TYPE
			OBJECTS { outputPTPimageShelfIndex, outputPTPimageSlotIndex, outputPTPimageCurrentImage }
			STATUS current
			DESCRIPTION
				"SM2000-5G output PTP card image id configuration trap object which specifies next boot image id"
			::={ inputOutput 27 }

		-- 1.3.6.1.4.1.43913.16.8.28
		sm2000TrapOutputPTPNetwork NOTIFICATION-TYPE
			OBJECTS { outputPTPNetworkConfigShelfIndex, outputPTPNetworkConfigSlotIndex, outputPTPNetworkConfigPortIndex, outputPTPNetworkConfigIpState, outputPTPNetworkConfigIpInfo, outputPTPNetworkConfigVlanMode  }
			STATUS current
			DESCRIPTION
				"SM2000-5G output PTP card network configuration trap object which specifies ip-state, ip-info, vlan-mode"
			::={ inputOutput 28 }

        	-- 1.3.6.1.4.1.43913.16.8.29
		sm2000TrapOutputPTPMulticast NOTIFICATION-TYPE
			OBJECTS { outputPTPMulticastShelfIndex,outputPTPMulticastSlotIndex,outputPTPMulticastPortIndex,outputPTPMulticastVlanID,outputPTPMulticastSyncIntv,outputPTPMulticastAnnounceIntv,outputPTPMulticastDelayIntv,outputPTPMulticastAnnounceTimeout,outputPTPMulticastClientTimeout}
			STATUS current
			DESCRIPTION
				"SM2000-5G output PTP card multicast configuration trap object which specifies vlan-id, sync-interval, announce-interval, delay-interval, announce-timeout, client-timeout"
			::={ inputOutput 29 }

		-- 1.3.6.1.4.1.43913.16.8.30
		sm2000TrapOutputPTPSynce NOTIFICATION-TYPE
			OBJECTS { outputPTPSynceShelfIndex, outputPTPSynceSlotIndex, outputPTPSyncePortIndex, outputPTPSynceESMCstate, outputPTPSynceQLstate, outputPTPSynceOutQLmode  }
			STATUS current
			DESCRIPTION
				"SM2000-5G output PTP card SyncE configuration trap object which specifies ESMC-state, QL-state, out-QL-mode"
			::={ inputOutput 30 }

		-- 1.3.6.1.4.1.43913.16.8.31
		sm2000TrapOutputPTPCommon NOTIFICATION-TYPE
			OBJECTS { outputPTPCommonConfigShelfIndex,outputPTPCommonConfigSlotIndex,outputPTPCommonConfigPTPstate,outputPTPCommonConfigMaxClients,outputPTPCommonConfigProfile,outputPTPCommonConfigClockID,outputPTPCommonConfigPriority1,outputPTPCommonConfigPriority2,outputPTPCommonConfigDomain,outputPTPCommonConfigDSCP,outputPTPCommonConfigDSCPstate,outputPTPCommonConfigSyncLimit,outputPTPCommonConfigAnnounceLimit,outputPTPCommonConfigDelayLimit,outputPTPCommonConfigTwoStep,outputPTPCommonConfigTTL,outputPTPCommonConfigMgmtAddrMode,outputPTPCommonConfigAlternateMaster,outputPTPCommonConfigUnicastNegotiate,outputPTPCommonConfigUnicastLeaseDuration }
			STATUS current
			DESCRIPTION
				"SM2000-5G output PTP card common configuration trap object which specifies time-scale, ptp-state, max clients, profile, clock-id, priority1, priority2, domain, DSCP, DSCP-state, Sync-limit, announce-limit, delay-limit, two-step, TTL, management-addr-mode, alternate-master, unicast-negotiate, unicast-lease-duration, dither-state"
			::={ inputOutput 31 }

		-- 1.3.6.1.4.1.43913.16.8.32
		sm2000TrapIOstatus NOTIFICATION-TYPE
			OBJECTS { ioStatusIndex, ioStatusSlotID, ioType, ioSignal, ioStatusRedundancy, ioStatusActive, outputRedundancyMode}
			STATUS current
			DESCRIPTION
				"SM2000-5G input-output card info trap object which specifies ioType, signal, refundancy-state, active-status, redundancy-mode"
			::={ inputOutput 32 }

		-- 1.3.6.1.4.1.43913.16.8.33
		sm2000TrapOutputPTPntpClientMonstatus NOTIFICATION-TYPE
			OBJECTS { outputPTPntpClientMonShelfIndex, outputPTPntpClientMonSlotIndex, outputPTPntpClientMonPortIndex, outputPTPntpClientMonIpIndex, outputPTPntpClientMonIp, outputPTPntpClientMonThresholdExceedStatus}
			STATUS current
			DESCRIPTION
				"SM2000-5G input-output card info trap object which specifies ioType, signal, refundancy-state, active-status, redundancy-mode"
			::={ inputOutput 33 }

		output10GE OBJECT IDENTIFIER ::= { inputOutput 34 }

			output10GEinventoryTable OBJECT-TYPE
				SYNTAX SEQUENCE OF Output10GEinventoryEntry
				MAX-ACCESS not-accessible
				STATUS current
				DESCRIPTION
					"The table of output ptp card inventory info."
				::= {output10GE 1}

			-- 1.3.6.1.4.1.43913.16.8.34.1.1
			output10GEinventoryEntry OBJECT-TYPE
				SYNTAX  Output10GEinventoryEntry
				MAX-ACCESS not-accessible
				STATUS current
				DESCRIPTION
					"The entry of output ptp card inventory info."
				INDEX { output10GEinventoryShelfIndex, output10GEinventorySlotIndex }
				::= {output10GEinventoryTable 1}

			Output10GEinventoryEntry ::=
				SEQUENCE{
					output10GEinventoryShelfIndex
						Integer32,
					output10GEinventorySlotIndex
						Integer32,
					output10GEinventoryPartNum
						DisplayString,
					output10GEinventorySerialNum
						DisplayString,
					output10GEinventoryCLEINum
						DisplayString,
					output10GEinventoryHwNum
						DisplayString,
					output10GEinventorySwNum
						DisplayString,
					output10GEinventoryFPGAVersion
						DisplayString,
					output10GEinventoryCompatibilityNum
						DisplayString
				}

			-- 1.3.6.1.4.1.43913.16.8.34.1.1.1
			output10GEinventoryShelfIndex OBJECT-TYPE
				SYNTAX Integer32 (0..4)
				MAX-ACCESS not-accessible
				STATUS current
				DESCRIPTION
					"The index: main(0), exp1(1), exp2(2), exp3(3), exp4(4)"
				::= {output10GEinventoryEntry 1}

			-- 1.3.6.1.4.1.43913.16.8.34.1.1.2
			output10GEinventorySlotIndex OBJECT-TYPE
				SYNTAX Integer32 (0..14)
				MAX-ACCESS not-accessible
				STATUS current
				DESCRIPTION
					"The slot index. When the index is 0(main), the slot-index range is 2~9;
					When the index is 1~4(exp1~exp4), the slot-index range is 3~14"
				::= {output10GEinventoryEntry 2}

			-- 1.3.6.1.4.1.43913.16.8.34.1.1.3
			output10GEinventoryPartNum OBJECT-TYPE
				SYNTAX DisplayString
				MAX-ACCESS read-only
				STATUS current
				DESCRIPTION
					"The part number of output-ptp card"
				::= {output10GEinventoryEntry 3}

			-- 1.3.6.1.4.1.43913.16.8.34.1.1.4
			output10GEinventorySerialNum OBJECT-TYPE
				SYNTAX DisplayString
				MAX-ACCESS read-only
				STATUS current
				DESCRIPTION
					"The serial number of output-ptp card"
				::= {output10GEinventoryEntry 4}

			-- 1.3.6.1.4.1.43913.16.8.34.1.1.5
			output10GEinventoryCLEINum OBJECT-TYPE
				SYNTAX DisplayString
				MAX-ACCESS read-only
				STATUS current
				DESCRIPTION
					"The CLEI number of output-ptp card"
				::= {output10GEinventoryEntry 5}

			-- 1.3.6.1.4.1.43913.16.8.34.1.1.6
			output10GEinventoryHwNum OBJECT-TYPE
				SYNTAX DisplayString
				MAX-ACCESS read-only
				STATUS current
				DESCRIPTION
					"The hardware number of output-ptp card"
				::= {output10GEinventoryEntry 6}

			-- 1.3.6.1.4.1.43913.16.8.34.1.1.7
			output10GEinventorySwNum OBJECT-TYPE
				SYNTAX DisplayString
				MAX-ACCESS read-only
				STATUS current
				DESCRIPTION
					"The software number of output-ptp card"
				::= {output10GEinventoryEntry 7}

			-- 1.3.6.1.4.1.43913.16.8.34.1.1.8
				output10GEinventoryFPGAVersion OBJECT-TYPE
					SYNTAX DisplayString
					MAX-ACCESS read-only
					STATUS current
					DESCRIPTION
						"The FPGA version of output-ptp card"
					::= {output10GEinventoryEntry 8}

			-- 1.3.6.1.4.1.43913.16.8.34.1.1.9
			output10GEinventoryCompatibilityNum OBJECT-TYPE
				SYNTAX DisplayString
				MAX-ACCESS read-only
				STATUS current
				DESCRIPTION
					"The compatibility number of output-ptp card"
				::= {output10GEinventoryEntry 9}


			-- 1.3.6.1.4.1.43913.16.8.34.2
			output10GEimageTable OBJECT-TYPE
				SYNTAX SEQUENCE OF Output10GEimageEntry
				MAX-ACCESS not-accessible
				STATUS current
				DESCRIPTION
					"The table of output ptp card image info."
				::= {output10GE 2}

			-- 1.3.6.1.4.1.43913.16.8.34.2.1
			output10GEimageEntry OBJECT-TYPE
				SYNTAX  Output10GEimageEntry
				MAX-ACCESS not-accessible
				STATUS current
				DESCRIPTION
					"The entry of output ptp card image info."
				INDEX { output10GEimageShelfIndex, output10GEimageSlotIndex }
				::= {output10GEimageTable 1}

			Output10GEimageEntry ::=
				SEQUENCE{
				output10GEimageShelfIndex
						Integer32,
				output10GEimageSlotIndex
						Integer32,
				output10GEimageActiveImage
						Integer32,
				output10GEimageActiveVersion
						DisplayString,
				output10GEimageBackupImage
						Integer32,
				output10GEimageBackupVersion
						DisplayString,
				output10GEimageCurrentImage
						Integer32
				}

			-- 1.3.6.1.4.1.43913.16.8.34.2.1.1
			output10GEimageShelfIndex OBJECT-TYPE
				SYNTAX Integer32 (0..4)
				MAX-ACCESS not-accessible
				STATUS current
				DESCRIPTION
					"The index: main(0), exp1(1), exp2(2), exp3(3), exp4(4)"
				::= {output10GEimageEntry 1}

			-- 1.3.6.1.4.1.43913.16.8.34.2.1.2
			output10GEimageSlotIndex OBJECT-TYPE
				SYNTAX Integer32 (0..14)
				MAX-ACCESS not-accessible
				STATUS current
				DESCRIPTION
					"The slot index. When the index is 0(main), the slot-index range is 2~9;
					When the index is 1~4(exp1~exp4), the slot-index range is 3~14"
				::= {output10GEimageEntry 2}

			-- 1.3.6.1.4.1.43913.16.8.34.2.1.3
			output10GEimageActiveImage OBJECT-TYPE
				SYNTAX Integer32
				MAX-ACCESS read-only
				STATUS current
				DESCRIPTION
					"The active image id"
				::= {output10GEimageEntry 3}

			-- 1.3.6.1.4.1.43913.16.8.34.2.1.4
			output10GEimageActiveVersion OBJECT-TYPE
				SYNTAX DisplayString
				MAX-ACCESS read-only
				STATUS current
				DESCRIPTION
					"The active image version info"
				::= {output10GEimageEntry 4}

			-- 1.3.6.1.4.1.43913.16.8.34.2.1.5
			output10GEimageBackupImage OBJECT-TYPE
				SYNTAX Integer32
				MAX-ACCESS read-only
				STATUS current
				DESCRIPTION
					"The backup image id"
				::= {output10GEimageEntry 5}

			-- 1.3.6.1.4.1.43913.16.8.34.2.1.6
			output10GEimageBackupVersion OBJECT-TYPE
				SYNTAX DisplayString
				MAX-ACCESS read-only
				STATUS current
				DESCRIPTION
					"The backup image version info"
				::= {output10GEimageEntry 6}

			-- 1.3.6.1.4.1.43913.16.8.34.2.1.7
			output10GEimageCurrentImage OBJECT-TYPE
				SYNTAX Integer32  (1..2)
				MAX-ACCESS read-write
				STATUS current
				DESCRIPTION
					"The current next boot up image id."
				::= {output10GEimageEntry 7}


			-- 1.3.6.1.4.1.43913.16.8.34.3
			output10GENetworkConfigTable OBJECT-TYPE
				SYNTAX SEQUENCE OF Output10GENetworkConfigEntry
				MAX-ACCESS not-accessible
				STATUS current
				DESCRIPTION
					"The table of output ptp card Network config info."
				::= {output10GE 3}

			-- 1.3.6.1.4.1.43913.16.8.34.3.1
			output10GENetworkConfigEntry OBJECT-TYPE
				SYNTAX  Output10GENetworkConfigEntry
				MAX-ACCESS not-accessible
				STATUS current
				DESCRIPTION
					"The entry of output ptp card Network config info."
				INDEX { output10GENetworkConfigShelfIndex, output10GENetworkConfigSlotIndex, output10GENetworkConfigPortIndex }
				::= {output10GENetworkConfigTable 1}

			Output10GENetworkConfigEntry ::=
				SEQUENCE{
				output10GENetworkConfigShelfIndex
						Integer32,
				output10GENetworkConfigSlotIndex
						Integer32,
				output10GENetworkConfigPortIndex
						Integer32,
				output10GENetworkConfigIpState
						ActionState,
				output10GENetworkConfigIpInfo
						DisplayString,
				output10GENetworkConfigVlanMode
						ActionState,
				output10GENetworkConfigAutoNegState
						ActionState,
				output10GENetworkConfigSpeed
						EthLinkSpeedCfg10GE,
				output10GENetworkConfigDuplex
						EthlinkDuplexType,
				output10GENetworkConfigIpType
						EthPortIpType
				}

			-- 1.3.6.1.4.1.43913.16.8.34.3.1.1
			output10GENetworkConfigShelfIndex OBJECT-TYPE
				SYNTAX Integer32 (0..4)
				MAX-ACCESS not-accessible
				STATUS current
				DESCRIPTION
					"The shelf index: main(0), exp1(1), exp2(2), exp3(3), exp4(4)"
				::= {output10GENetworkConfigEntry 1}

			-- 1.3.6.1.4.1.43913.16.8.34.3.1.2
			output10GENetworkConfigSlotIndex OBJECT-TYPE
				SYNTAX Integer32 (0..14)
				MAX-ACCESS not-accessible
				STATUS current
				DESCRIPTION
					"The slot index. When the index is 0(main), the slot-index range is 2~9;
					When the  index is 1~4(exp1~exp4), the slot-index range is 3~14"
				::= {output10GENetworkConfigEntry 2}

			-- 1.3.6.1.4.1.43913.16.8.34.3.1.3
			output10GENetworkConfigPortIndex OBJECT-TYPE
				SYNTAX Integer32 (1..4)
				MAX-ACCESS not-accessible
				STATUS current
				DESCRIPTION
					"The port index: 1~4"
				::= {output10GENetworkConfigEntry 3}

			-- 1.3.6.1.4.1.43913.16.8.34.3.1.4
			output10GENetworkConfigIpState  OBJECT-TYPE
				SYNTAX ActionState
				MAX-ACCESS read-write
				STATUS current
				DESCRIPTION
					"The ip state of output-ptp card port. disable(0), enable(1)"
				::={output10GENetworkConfigEntry 4}

			-- 1.3.6.1.4.1.43913.16.8.34.3.1.5
			output10GENetworkConfigIpInfo  OBJECT-TYPE
				SYNTAX DisplayString
				MAX-ACCESS read-write
				STATUS current
				DESCRIPTION
					"The format is : address,netmask,gateway"
				::={output10GENetworkConfigEntry 5}

			-- 1.3.6.1.4.1.43913.16.8.34.3.1.6
			output10GENetworkConfigVlanMode  OBJECT-TYPE
				SYNTAX ActionState
				MAX-ACCESS read-write
				STATUS current
				DESCRIPTION
					"The vlan mode of output-ptp card port. disable(0), enable(1)"
				::={output10GENetworkConfigEntry 6}

			-- 1.3.6.1.4.1.43913.16.8.34.3.1.7
			output10GENetworkConfigAutoNegState  OBJECT-TYPE
				SYNTAX ActionState
				MAX-ACCESS read-write
				STATUS current
				DESCRIPTION
					"The state of output-ptp card auto negotiation. disable(0), enable(1)"
				::={output10GENetworkConfigEntry 7}

			-- 1.3.6.1.4.1.43913.16.8.34.3.1.8
			output10GENetworkConfigSpeed  OBJECT-TYPE
				SYNTAX EthLinkSpeedCfg10GE
				MAX-ACCESS read-write
				STATUS current
				DESCRIPTION
					"The speed of output-ptp card port. 1000M(2), 10000M(3)"
				::={output10GENetworkConfigEntry 8}

			-- 1.3.6.1.4.1.43913.16.8.34.3.1.9
			output10GENetworkConfigDuplex  OBJECT-TYPE
				SYNTAX EthlinkDuplexType
				MAX-ACCESS read-write
				STATUS current
				DESCRIPTION
					"The duplex type of output-ptp card port. full(0), half(1)"
				::={output10GENetworkConfigEntry 9}

			-- 1.3.6.1.4.1.43913.16.8.34.3.1.10
			output10GENetworkConfigIpType  OBJECT-TYPE
				SYNTAX EthPortIpType
				MAX-ACCESS read-write
				STATUS current
				DESCRIPTION
					"The IP type of output-ptp card port. IPv4(0), IPv6(1)"
				::={output10GENetworkConfigEntry 10}


			-- 1.3.6.1.4.1.43913.16.8.34.4
			output10GEboardConfigManageTable OBJECT-TYPE
				SYNTAX SEQUENCE OF Output10GEboardConfigManageEntry
				MAX-ACCESS not-accessible
				STATUS current
				DESCRIPTION
					"The table of output ptp board config management."
				::={output10GE 4}

			-- 1.3.6.1.4.1.43913.16.8.34.4.1
			output10GEboardConfigManageEntry OBJECT-TYPE
				SYNTAX  Output10GEboardConfigManageEntry
				MAX-ACCESS not-accessible
				STATUS current
				DESCRIPTION
					"The entry of output ptp board config management."
				INDEX { output10GEboardConfigManageShelfIndex, output10GEboardConfigManageSlotIndex }
				::={output10GEboardConfigManageTable 1}

			Output10GEboardConfigManageEntry ::=
				SEQUENCE{
				output10GEboardConfigManageShelfIndex
						Integer32,
				output10GEboardConfigManageSlotIndex
						Integer32,
				output10GEboardConfigManageBackup
						ActionApply,
				output10GEboardConfigManageRestore
						Integer32
				}

			-- 1.3.6.1.4.1.43913.16.8.34.4.1.1
			output10GEboardConfigManageShelfIndex OBJECT-TYPE
				SYNTAX Integer32 (0..4)
				MAX-ACCESS not-accessible
				STATUS current
				DESCRIPTION
					"The shelf index: main(0), exp1(1), exp2(2), exp3(3), exp4(4)"
				::={output10GEboardConfigManageEntry 1}

			-- 1.3.6.1.4.1.43913.16.8.34.4.1.2
			output10GEboardConfigManageSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEboardConfigManageEntry 2}

			-- 1.3.6.1.4.1.43913.16.8.34.4.1.3
			output10GEboardConfigManageBackup  OBJECT-TYPE
				SYNTAX   ActionApply
				MAX-ACCESS write-only
				STATUS current
				DESCRIPTION
					"Backup config of output ptp card locally."
				::={output10GEboardConfigManageEntry 3}

			-- 1.3.6.1.4.1.43913.16.8.34.4.1.4
			output10GEboardConfigManageRestore  OBJECT-TYPE
				SYNTAX   Integer32   (0..1)
				MAX-ACCESS write-only
				STATUS current
				DESCRIPTION
					"Restore config of output ptp card. 0--dafault config; 1--factory config"
				::={output10GEboardConfigManageEntry 4}


			-- 1.3.6.1.4.1.43913.16.8.34.5
			output10GEntpAuthenticaConfigTable OBJECT-TYPE
				SYNTAX SEQUENCE OF Output10GEntpAuthenticaConfigEntry
				MAX-ACCESS not-accessible
				STATUS current
				DESCRIPTION
					"The table of output ptp ntp authentica."
				::={output10GE 5}

			-- 1.3.6.1.4.1.43913.16.8.34.5.1
			output10GEntpAuthenticaConfigEntry OBJECT-TYPE
				SYNTAX  Output10GEntpAuthenticaConfigEntry
				MAX-ACCESS not-accessible
				STATUS current
				DESCRIPTION
					"The entry of output ptp ntp whitelist."
				INDEX { output10GEntpAuthenticaConfigShelfIndex, output10GEntpAuthenticaConfigSlotIndex, output10GEntpAuthenticaConfigPortIndex }
				::={output10GEntpAuthenticaConfigTable 1}

			Output10GEntpAuthenticaConfigEntry ::=
				SEQUENCE{
				output10GEntpAuthenticaConfigShelfIndex
						Integer32,
				output10GEntpAuthenticaConfigSlotIndex
						Integer32,
				output10GEntpAuthenticaConfigPortIndex
						Integer32,
				output10GEntpAuthenticaConfigAutokeyState
						ActionState,
				output10GEntpAuthenticaConfigMD5State
						ActionState
				}

			-- 1.3.6.1.4.1.43913.16.8.34.6.1.1
			output10GEntpAuthenticaConfigShelfIndex OBJECT-TYPE
				SYNTAX Integer32 (0..4)
				MAX-ACCESS not-accessible
				STATUS current
				DESCRIPTION
					"The shelf index: main(0), exp1(1), exp2(2), exp3(3), exp4(4)"
				::={output10GEntpAuthenticaConfigEntry 1}

			-- 1.3.6.1.4.1.43913.16.8.34.5.1.2
			output10GEntpAuthenticaConfigSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEntpAuthenticaConfigEntry 2}

			-- 1.3.6.1.4.1.43913.16.8.34.5.1.3
			output10GEntpAuthenticaConfigPortIndex OBJECT-TYPE
				SYNTAX Integer32 (1..4)
				MAX-ACCESS not-accessible
				STATUS current
				DESCRIPTION
					"The port index. "
				::={output10GEntpAuthenticaConfigEntry 3}

			-- 1.3.6.1.4.1.43913.16.8.34.5.1.4
			output10GEntpAuthenticaConfigAutokeyState  OBJECT-TYPE
				SYNTAX   ActionState
				MAX-ACCESS read-write
				STATUS current
				DESCRIPTION
					"The state of NTP authentica autokey. enable(1), disable(0)."
				::={output10GEntpAuthenticaConfigEntry 4}

		-- 1.3.6.1.4.1.43913.16.8.34.5.1.5
			output10GEntpAuthenticaConfigMD5State  OBJECT-TYPE
				SYNTAX   ActionState
				MAX-ACCESS read-write
				STATUS current
				DESCRIPTION
					"The state of NTP authentica MD5. enable(1), disable(0)."
				::={output10GEntpAuthenticaConfigEntry 5}

		-- 1.3.6.1.4.1.43913.16.8.34.6
			output10GEntpAuthenticaKeysTable OBJECT-TYPE
				SYNTAX SEQUENCE OF Output10GEntpAuthenticaKeysEntry
				MAX-ACCESS not-accessible
				STATUS current
				DESCRIPTION
					"The table of output ptp ntp authentica."
				::={output10GE 6}

			-- 1.3.6.1.4.1.43913.16.8.34.6.1
			output10GEntpAuthenticaKeysEntry OBJECT-TYPE
				SYNTAX  Output10GEntpAuthenticaKeysEntry
				MAX-ACCESS not-accessible
				STATUS current
				DESCRIPTION
					"The entry of output ptp ntp whitelist."
				INDEX { output10GEntpAuthenticaKeysShelfIndex, output10GEntpAuthenticaKeysSlotIndex, output10GEntpAuthenticaKeysPortIndex }
				::={output10GEntpAuthenticaKeysTable 1}

			Output10GEntpAuthenticaKeysEntry ::=
				SEQUENCE{
				output10GEntpAuthenticaKeysShelfIndex
						Integer32,
				output10GEntpAuthenticaKeysSlotIndex
						Integer32,
				output10GEntpAuthenticaKeysPortIndex
						Integer32,
				output10GEntpAuthenticaKeysAutokey
						DisplayString,
				output10GEntpAuthenticaKeysMD5key
						DisplayString
				}

			-- 1.3.6.1.4.1.43913.16.8.34.6.1.1
			output10GEntpAuthenticaKeysShelfIndex OBJECT-TYPE
				SYNTAX Integer32 (0..4)
				MAX-ACCESS not-accessible
				STATUS current
				DESCRIPTION
					"The shelf index: main(0), exp1(1), exp2(2), exp3(3), exp4(4)"
				::={output10GEntpAuthenticaKeysEntry 1}

			-- 1.3.6.1.4.1.43913.16.8.34.6.1.2
			output10GEntpAuthenticaKeysSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEntpAuthenticaKeysEntry 2}

			-- 1.3.6.1.4.1.43913.16.8.34.6.1.3
			output10GEntpAuthenticaKeysPortIndex OBJECT-TYPE
				SYNTAX Integer32 (1..4)
				MAX-ACCESS not-accessible
				STATUS current
				DESCRIPTION
					"The port index."
				::={output10GEntpAuthenticaKeysEntry 3}

		-- 1.3.6.1.4.1.43913.16.8.34.6.1.4
			output10GEntpAuthenticaKeysAutokey  OBJECT-TYPE
				SYNTAX   DisplayString
				MAX-ACCESS read-only
				STATUS current
				DESCRIPTION
					"The autokey key value of NTP authentica."
				::={output10GEntpAuthenticaKeysEntry 4}

		-- 1.3.6.1.4.1.43913.16.8.34.6.1.5
			output10GEntpAuthenticaKeysMD5key  OBJECT-TYPE
				SYNTAX   DisplayString
				MAX-ACCESS read-only
				STATUS current
				DESCRIPTION
					"The MD5 key value of NTP authentica."
				::={output10GEntpAuthenticaKeysEntry 5}


		-- 1.3.6.1.4.1.43913.16.8.34.7
			output10GEntplistConfigTable OBJECT-TYPE
				SYNTAX SEQUENCE OF Output10GEntplistConfigEntry
				MAX-ACCESS not-accessible
				STATUS current
				DESCRIPTION
					"The table of output ptp ntp list state."
				::={output10GE 7}

			-- 1.3.6.1.4.1.43913.16.8.34.7.1
			output10GEntplistConfigEntry OBJECT-TYPE
				SYNTAX  Output10GEntplistConfigEntry
				MAX-ACCESS not-accessible
				STATUS current
				DESCRIPTION
					"The entry of output ptp ntp whitelist."
				INDEX { output10GEntplistConfigShelfIndex, output10GEntplistConfigSlotIndex, output10GEntplistConfigPortIndex }
				::={output10GEntplistConfigTable 1}

			Output10GEntplistConfigEntry ::=
				SEQUENCE{
				output10GEntplistConfigShelfIndex
						Integer32,
				output10GEntplistConfigSlotIndex
						Integer32,
				output10GEntplistConfigPortIndex
						Integer32,
				output10GEntpListState
						NtpListState
				}

			-- 1.3.6.1.4.1.43913.16.8.34.7.1.1
			output10GEntplistConfigShelfIndex OBJECT-TYPE
				SYNTAX Integer32 (0..4)
				MAX-ACCESS not-accessible
				STATUS current
				DESCRIPTION
					"The shelf index: main(0), exp1(1), exp2(2), exp3(3), exp4(4)"
				::={output10GEntplistConfigEntry 1}

			-- 1.3.6.1.4.1.43913.16.8.34.7.1.2
			output10GEntplistConfigSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEntplistConfigEntry 2}

			-- 1.3.6.1.4.1.43913.16.8.34.7.1.3
			output10GEntplistConfigPortIndex  OBJECT-TYPE
				SYNTAX   Integer32 (1..4)
				MAX-ACCESS not-accessible
				STATUS current
				DESCRIPTION
					"The whitelist addr index."
				::={output10GEntplistConfigEntry 3}

			-- 1.3.6.1.4.1.43913.16.8.34.7.1.4
			output10GEntpListState  OBJECT-TYPE
				SYNTAX   NtpListState
				MAX-ACCESS read-write
				STATUS current
				DESCRIPTION
					"The ntp list state. none(0), whitelist(1), blacklist(2)"
				::={output10GEntplistConfigEntry 4}


			-- 1.3.6.1.4.1.43913.16.8.34.8
			output10GEntpWhitelistTable OBJECT-TYPE
				SYNTAX SEQUENCE OF Output10GEntpWhitelistEntry
				MAX-ACCESS not-accessible
				STATUS current
				DESCRIPTION
					"The table of output ptp ntp whitelist."
				::={output10GE 8}

			-- 1.3.6.1.4.1.43913.16.8.34.8.1
			output10GEntpWhitelistEntry OBJECT-TYPE
				SYNTAX  Output10GEntpWhitelistEntry
				MAX-ACCESS not-accessible
				STATUS current
				DESCRIPTION
					"The entry of output ptp ntp whitelist."
				INDEX { output10GEntpWhitelistShelfIndex, output10GEntpWhitelistSlotIndex, output10GEntpWhitelistPortIndex, output10GEntpWhitelistIndex }
				::={output10GEntpWhitelistTable 1}

			Output10GEntpWhitelistEntry ::=
				SEQUENCE{
				output10GEntpWhitelistShelfIndex
						Integer32,
				output10GEntpWhitelistSlotIndex
						Integer32,
				output10GEntpWhitelistPortIndex
						Integer32,
				output10GEntpWhitelistIndex
						Integer32,
				output10GEntpWhitelistAddr
						DisplayString,
				output10GEntpWhitelistCount
						Integer32,
				output10GEntpWhitelistRowStatus
						RowStatus
				}

			-- 1.3.6.1.4.1.43913.16.8.34.8.1.1
			output10GEntpWhitelistShelfIndex OBJECT-TYPE
				SYNTAX Integer32 (0..4)
				MAX-ACCESS not-accessible
				STATUS current
				DESCRIPTION
					"The shelf index: main(0), exp1(1), exp2(2), exp3(3), exp4(4)"
				::={output10GEntpWhitelistEntry 1}

			-- 1.3.6.1.4.1.43913.16.8.34.8.1.2
			output10GEntpWhitelistSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEntpWhitelistEntry 2}

			-- 1.3.6.1.4.1.43913.16.8.34.8.1.3
			output10GEntpWhitelistPortIndex OBJECT-TYPE
				SYNTAX Integer32 (1..4)
				MAX-ACCESS not-accessible
				STATUS current
				DESCRIPTION
					"The slot index. "
				::={output10GEntpWhitelistEntry 3}

			-- 1.3.6.1.4.1.43913.16.8.34.8.1.4
			output10GEntpWhitelistIndex  OBJECT-TYPE
				SYNTAX   Integer32
				MAX-ACCESS not-accessible
				STATUS current
				DESCRIPTION
					"The whitelist addr index."
				::={output10GEntpWhitelistEntry 4}

			-- 1.3.6.1.4.1.43913.16.8.34.8.1.5
			output10GEntpWhitelistAddr  OBJECT-TYPE
				SYNTAX   DisplayString
				MAX-ACCESS read-write
				STATUS current
				DESCRIPTION
					"The whitelist addr: xxx.xxx.xxx.xxx or xxx.xxx.xxx.xxx,xxx.xxx.xxx.xxx."
				::={output10GEntpWhitelistEntry 5}


			-- 1.3.6.1.4.1.43913.16.8.34.8.1.6
			output10GEntpWhitelistCount  OBJECT-TYPE
				SYNTAX   Integer32
				MAX-ACCESS read-only
				STATUS current
				DESCRIPTION
					"The whitelist count."
				::={output10GEntpWhitelistEntry 6}

			-- 1.3.6.1.4.1.43913.16.8.34.8.1.7
			output10GEntpWhitelistRowStatus OBJECT-TYPE
				SYNTAX RowStatus
				MAX-ACCESS read-write
				STATUS current
				DESCRIPTION
					"The row status of NTP whitelist table to control row actions. It has the following actions:

					The status column has six defined values:

						- `active(1)', which indicates that the conceptual row is
						available for use by the managed device;

						- `notInService(2)', which indicates that the conceptual
						row exists in the agent, but is unavailable for use by
						the managed device (see NOTE below);

						- `notReady(3)', which indicates that the conceptual row
						exists in the agent, but is missing information
						necessary in order to be available for use by the
						managed device;

						- `createAndGo(4)', which is supplied by a management
						station wishing to create a new instance of a
						conceptual row and to have its status automatically set
						to active, making it available for use by the managed
						device;

						- `createAndWait(5)', which is supplied by a management
						station wishing to create a new instance of a
						conceptual row (but not make it available for use by
						the managed device); and,

						- `destroy(6)', which is supplied by a management station
						wishing to delete all of the instances associated with
						an existing conceptual row.
					"
				::= { output10GEntpWhitelistEntry 7 }


			-- 1.3.6.1.4.1.43913.16.8.34.9
			output10GEntpBlacklistTable OBJECT-TYPE
				SYNTAX SEQUENCE OF Output10GEntpBlacklistEntry
				MAX-ACCESS not-accessible
				STATUS current
				DESCRIPTION
					"The table of output ptp ntp Blacklist."
				::={output10GE 9}

			-- 1.3.6.1.4.1.43913.16.8.34.9.1
			output10GEntpBlacklistEntry OBJECT-TYPE
				SYNTAX  Output10GEntpBlacklistEntry
				MAX-ACCESS not-accessible
				STATUS current
				DESCRIPTION
					"The entry of output ptp ntp Blacklist."
				INDEX { output10GEntpBlacklistShelfIndex, output10GEntpBlacklistSlotIndex, output10GEntpBlacklistPortIndex, output10GEntpBlacklistIndex }
				::={output10GEntpBlacklistTable 1}

			Output10GEntpBlacklistEntry ::=
				SEQUENCE{
				output10GEntpBlacklistShelfIndex
						Integer32,
				output10GEntpBlacklistSlotIndex
						Integer32,
				output10GEntpBlacklistPortIndex
						Integer32,
				output10GEntpBlacklistIndex
						Integer32,
				output10GEntpBlacklistAddr
						DisplayString,
				output10GEntpBlacklistCount
						Integer32,
				output10GEntpBlacklistRowStatus
						RowStatus
				}

			-- 1.3.6.1.4.1.43913.16.8.34.9.1.1
			output10GEntpBlacklistShelfIndex OBJECT-TYPE
				SYNTAX Integer32 (0..4)
				MAX-ACCESS not-accessible
				STATUS current
				DESCRIPTION
					"The shelf index: main(0), exp1(1), exp2(2), exp3(3), exp4(4)"
				::={output10GEntpBlacklistEntry 1}

			-- 1.3.6.1.4.1.43913.16.8.34.9.1.2
			output10GEntpBlacklistSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEntpBlacklistEntry 2}

			-- 1.3.6.1.4.1.43913.16.8.34.9.1.3
			output10GEntpBlacklistPortIndex OBJECT-TYPE
				SYNTAX Integer32 (1..4)
				MAX-ACCESS not-accessible
				STATUS current
				DESCRIPTION
					"The slot index. "
				::={output10GEntpBlacklistEntry 3}

			-- 1.3.6.1.4.1.43913.16.8.34.9.1.4
			output10GEntpBlacklistIndex  OBJECT-TYPE
				SYNTAX   Integer32
				MAX-ACCESS not-accessible
				STATUS current
				DESCRIPTION
					"The Blacklist addr index."
				::={output10GEntpBlacklistEntry 4}

			-- 1.3.6.1.4.1.43913.16.8.34.9.1.5
			output10GEntpBlacklistAddr  OBJECT-TYPE
				SYNTAX   DisplayString
				MAX-ACCESS read-write
				STATUS current
				DESCRIPTION
					"The Blacklist addr : xxx.xxx.xxx.xxx or xxx.xxx.xxx.xxx,xxx.xxx.xxx.xxx"
				::={output10GEntpBlacklistEntry 5}

			-- 1.3.6.1.4.1.43913.16.8.34.9.1.6
			output10GEntpBlacklistCount  OBJECT-TYPE
				SYNTAX   Integer32
				MAX-ACCESS read-only
				STATUS current
				DESCRIPTION
					"The blacklist count."
				::={output10GEntpBlacklistEntry 6}

			-- 1.3.6.1.4.1.43913.16.8.34.9.1.7
			output10GEntpBlacklistRowStatus OBJECT-TYPE
				SYNTAX RowStatus
				MAX-ACCESS read-write
				STATUS current
				DESCRIPTION
					"The row status of NTP Blacklist table to control row actions. It has the following actions:

					The status column has six defined values:

						- `active(1)', which indicates that the conceptual row is
						available for use by the managed device;

						- `notInService(2)', which indicates that the conceptual
						row exists in the agent, but is unavailable for use by
						the managed device (see NOTE below);

						- `notReady(3)', which indicates that the conceptual row
						exists in the agent, but is missing information
						necessary in order to be available for use by the
						managed device;

						- `createAndGo(4)', which is supplied by a management
						station wishing to create a new instance of a
						conceptual row and to have its status automatically set
						to active, making it available for use by the managed
						device;

						- `createAndWait(5)', which is supplied by a management
						station wishing to create a new instance of a
						conceptual row (but not make it available for use by
						the managed device); and,

						- `destroy(6)', which is supplied by a management station
						wishing to delete all of the instances associated with
						an existing conceptual row.
					"
				::= { output10GEntpBlacklistEntry 7 }


			-- 1.3.6.1.4.1.43913.16.8.34.10
			output10GERestartTable OBJECT-TYPE
				SYNTAX SEQUENCE OF Output10GERestartEntry
				MAX-ACCESS not-accessible
				STATUS current
				DESCRIPTION
					"The table of output ptp restart action."
				::={output10GE 10}

			-- 1.3.6.1.4.1.43913.16.8.34.10.1
			output10GERestartEntry OBJECT-TYPE
				SYNTAX  Output10GERestartEntry
				MAX-ACCESS not-accessible
				STATUS current
				DESCRIPTION
					"The entry of output ptp restart action."
				INDEX { output10GERestartShelfIndex, output10GERestartSlotIndex, output10GERestartPortIndex }
				::={output10GERestartTable 1}

			Output10GERestartEntry ::=
				SEQUENCE{
				output10GERestartShelfIndex
						Integer32,
				output10GERestartSlotIndex
						Integer32,
				output10GERestartPortIndex
						Integer32,
				output10GERestartAction
						ActionApply,
				output10GERestartResult
						ActionResult
				}

			-- 1.3.6.1.4.1.43913.16.8.34.10.1.1
			output10GERestartShelfIndex OBJECT-TYPE
				SYNTAX Integer32 (0..4)
				MAX-ACCESS not-accessible
				STATUS current
				DESCRIPTION
					"The shelf index: main(0), exp1(1), exp2(2), exp3(3), exp4(4)"
				::={output10GERestartEntry 1}

			-- 1.3.6.1.4.1.43913.16.8.34.10.1.2
			output10GERestartSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GERestartEntry 2}

			-- 1.3.6.1.4.1.43913.16.8.34.10.1.3
			output10GERestartPortIndex OBJECT-TYPE
				SYNTAX Integer32 (0..4)
				MAX-ACCESS not-accessible
				STATUS current
				DESCRIPTION
					"The port index. 0 means the card, 1~4 means the port index"
				::={output10GERestartEntry 3}

			-- 1.3.6.1.4.1.43913.16.8.34.10.1.4
			output10GERestartAction OBJECT-TYPE
				SYNTAX ActionApply
				MAX-ACCESS write-only
				STATUS current
				DESCRIPTION
					" noapply(0), apply(1)"
				::={output10GERestartEntry 4}

			-- 1.3.6.1.4.1.43913.16.8.34.10.1.5
			output10GERestartResult OBJECT-TYPE
				SYNTAX ActionResult
				MAX-ACCESS read-only
				STATUS current
				DESCRIPTION
					" success(1), fail(2)"
				::={output10GERestartEntry 5}


			-- 1.3.6.1.4.1.43913.1.8.34.11
			output10GEclockStatusTable OBJECT-TYPE
				SYNTAX SEQUENCE OF Output10GEclockStatusEntry
				MAX-ACCESS not-accessible
				STATUS current
				DESCRIPTION
					"The table of output ptp clock status info."
				::={output10GE 11}

			-- 1.3.6.1.4.1.43913.1.8.34.11.1
			output10GEclockStatusEntry OBJECT-TYPE
				SYNTAX  Output10GEclockStatusEntry
				MAX-ACCESS not-accessible
				STATUS current
				DESCRIPTION
					"The entry of output ptp other status info."
				INDEX { output10GEclockStatusShelfIndex, output10GEclockStatusSlotIndex }
				::={output10GEclockStatusTable 1}

			Output10GEclockStatusEntry ::=
				SEQUENCE{
				output10GEclockStatusShelfIndex
						Integer32,
				output10GEclockStatusSlotIndex
						Integer32,
				output10GEclockState
						OutputPTPclockstateType,
				output10GEclockCurrentTime
						DisplayString,
				output10GEclockRunningTime
						DisplayString
				}

			-- 1.3.6.1.4.1.43913.1.8.34.11.1.1
			output10GEclockStatusShelfIndex OBJECT-TYPE
				SYNTAX Integer32 (0..4)
				MAX-ACCESS not-accessible
				STATUS current
				DESCRIPTION
					"The shelf index: main(0), exp1(1), exp2(2), exp3(3), exp4(4)"
				::={output10GEclockStatusEntry 1}

			-- 1.3.6.1.4.1.43913.1.8.34.11.1.2
			output10GEclockStatusSlotIndex OBJECT-TYPE
				SYNTAX Integer32 (0..14)
				MAX-ACCESS not-accessible
				STATUS current
				DESCRIPTION
					"The slot index. When the index is 0(main), the slot-index range is 2~9;
					When the  index is 1~4(exp1~exp4), the slot-index range is 3~14"
				::={output10GEclockStatusEntry 2}

			-- 1.3.6.1.4.1.43913.1.8.34.11.1.3
			output10GEclockState OBJECT-TYPE
				SYNTAX OutputPTPclockstateType
				MAX-ACCESS read-only
				STATUS current
				DESCRIPTION
					"The clock state of ptp output card clock"
				::={output10GEclockStatusEntry 3}

			-- 1.3.6.1.4.1.43913.1.8.34.11.1.4
			output10GEclockCurrentTime OBJECT-TYPE
				SYNTAX DisplayString
				MAX-ACCESS read-only
				STATUS current
				DESCRIPTION
					"The current time of ptp output card clock"
				::={output10GEclockStatusEntry 4}

			-- 1.3.6.1.4.1.43913.1.8.34.11.1.5
			output10GEclockRunningTime OBJECT-TYPE
				SYNTAX DisplayString
				MAX-ACCESS read-only
				STATUS current
				DESCRIPTION
					"The running time of ptp output card clock"
				::={output10GEclockStatusEntry 5}


			-- .1.3.6.1.4.1.43913.16.8.34
			output10GENetworkStatusTable OBJECT-TYPE
				SYNTAX SEQUENCE OF Output10GENetworkStatusEntry
				MAX-ACCESS not-accessible
				STATUS current
				DESCRIPTION
					"10GE output card network info table."
				::= { output10GE 12 }

			-- .1.3.6.1.4.1.43913.16.8.34.1
			output10GENetworkStatusEntry OBJECT-TYPE
				SYNTAX Output10GENetworkStatusEntry
				MAX-ACCESS not-accessible
				STATUS current
				DESCRIPTION
					"The entry of output 10GE network status table."
				INDEX { output10GEStatusNetworkShelfIndex, output10GEStatusNetworkSlotIndex, output10GEStatusNetworkEthPortID }
				::= { output10GENetworkStatusTable 1 }

			Output10GENetworkStatusEntry ::=
				SEQUENCE {
					output10GEStatusNetworkShelfIndex
						Integer32,
					output10GEStatusNetworkSlotIndex
						Integer32,
					output10GEStatusNetworkEthPortID
						Integer32,
					output10GEStatusNetworkHWAddr
						DisplayString
					}

			-- .1.3.6.1.4.1.43913.16.8.34.1.1
			output10GEStatusNetworkShelfIndex OBJECT-TYPE
				SYNTAX Integer32  (0..4)
				MAX-ACCESS not-accessible
				STATUS current
				DESCRIPTION
					"The shelf index: main(0), exp1(1), exp2(2), exp3(3), exp4(4)"
				::= { output10GENetworkStatusEntry 1 }

			-- .1.3.6.1.4.1.43913.16.8.34.1.2
			output10GEStatusNetworkSlotIndex OBJECT-TYPE
				SYNTAX Integer32  (0..14)
				MAX-ACCESS not-accessible
				STATUS current
				DESCRIPTION
					"The slot index. When the shelf index is 0(main), the slot-index range is 2~9;
					When the shelf index is 1~4(exp1~exp4), the slot-index range is 3~14"
				::= { output10GENetworkStatusEntry 2 }

			-- .1.3.6.1.4.1.43913.16.8.34.1.3
			output10GEStatusNetworkEthPortID OBJECT-TYPE
				SYNTAX Integer32
				MAX-ACCESS not-accessible
				STATUS current
				DESCRIPTION
					"IP port ID."
				::= { output10GENetworkStatusEntry 3 }

			-- .1.3.6.1.4.1.43913.16.8.34.1.4
			output10GEStatusNetworkHWAddr OBJECT-TYPE
				SYNTAX DisplayString
				MAX-ACCESS read-only
				STATUS current
				DESCRIPTION
					"HW address, type and other info of an ethernet port."
				::= { output10GENetworkStatusEntry 4 }


			-- 1.3.6.1.4.1.43913.16.8.34.13
			output10GEupgrade OBJECT IDENTIFIER ::= { output10GE 13 }

			-- 1.3.6.1.4.1.43913.16.8.34.13.1
			output10GEupgradeTable OBJECT-TYPE
				SYNTAX SEQUENCE OF Output10GEupgradeEntry
				MAX-ACCESS not-accessible
				STATUS current
				DESCRIPTION
					"This table is used to upgrade 10GE output card."
				::= { output10GEupgrade 1 }

			-- 1.3.6.1.4.1.43913.16.8.34.13.1.1
			output10GEupgradeEntry OBJECT-TYPE
				SYNTAX Output10GEupgradeEntry
				MAX-ACCESS not-accessible
				STATUS current
				DESCRIPTION
					"The entry of the table."
				INDEX { output10GEupgradeShelfIndex, output10GEupgradeSlotIndex }
				::= { output10GEupgradeTable 1 }

			Output10GEupgradeEntry ::=
				SEQUENCE {
					output10GEupgradeShelfIndex
						Integer32,
					output10GEupgradeSlotIndex
						Integer32,
					output10GEupgradeCmd
						DisplayString
				}

			-- 1.3.6.1.4.1.43913.16.8.34.13.1.1.1
			output10GEupgradeShelfIndex OBJECT-TYPE
				SYNTAX Integer32 (0..4)
				MAX-ACCESS not-accessible
				STATUS current
				DESCRIPTION
					"The shelf index: main(0), exp1(1), exp2(2), exp3(3), exp4(4)."
				::= { output10GEupgradeEntry 1 }

			-- 1.3.6.1.4.1.43913.16.8.34.13.1.1.2
			output10GEupgradeSlotIndex OBJECT-TYPE
				SYNTAX Integer32
				MAX-ACCESS read-only
				STATUS current
				DESCRIPTION
					"The slot index. When the index is 0(main), the slot-index range is 2~9;
					When the  index is 1~4(exp1~exp4), the slot-index range is 3~14."
				::= { output10GEupgradeEntry 2 }

			-- 1.3.6.1.4.1.43913.16.8.34.13.1.1.3
			output10GEupgradeCmd OBJECT-TYPE
				SYNTAX DisplayString
				MAX-ACCESS read-write
				STATUS current
				DESCRIPTION
					"The upgrade command, the format should be:file_name,[protocol:]server_ip,user,passwd."
				::= { output10GEupgradeEntry 3 }


			-- 1.3.6.1.4.1.43913.16.8.34.13.2
			output10GEupgradeStatusTable OBJECT-TYPE
				SYNTAX SEQUENCE OF Output10GEupgradeStatusEntry
				MAX-ACCESS not-accessible
				STATUS current
				DESCRIPTION
					"This table is used to get 10GE output card upgrade status."
				::= { output10GEupgrade 2 }

			-- 1.3.6.1.4.1.43913.16.8.34.13.2.1
			output10GEupgradeStatusEntry OBJECT-TYPE
				SYNTAX Output10GEupgradeStatusEntry
				MAX-ACCESS not-accessible
				STATUS current
				DESCRIPTION
					"The entry of the table."
				INDEX { output10GEupgradeStatusShelfIndex, output10GEupgradeStatusSlotIndex }
				::= { output10GEupgradeStatusTable 1 }

			Output10GEupgradeStatusEntry ::=
				SEQUENCE {
					output10GEupgradeStatusShelfIndex
						Integer32,
					output10GEupgradeStatusSlotIndex
						Integer32,
					output10GEupgradeStatus
						UpgradeStatus
				}

			-- 1.3.6.1.4.1.43913.16.8.34.13.2.1.1
			output10GEupgradeStatusShelfIndex OBJECT-TYPE
				SYNTAX Integer32
				MAX-ACCESS not-accessible
				STATUS current
				DESCRIPTION
					"The shelf index: main(0), exp1(1), exp2(2), exp3(3), exp4(4)."
				::= { output10GEupgradeStatusEntry 1 }

			-- 1.3.6.1.4.1.43913.16.8.34.13.2.1.2
			output10GEupgradeStatusSlotIndex OBJECT-TYPE
				SYNTAX Integer32
				MAX-ACCESS read-only
				STATUS current
				DESCRIPTION
					"The slot index. When the index is 0(main), the slot-index range is 2~9;
					When the  index is 1~4(exp1~exp4), the slot-index range is 3~14."
				::= { output10GEupgradeStatusEntry 2 }

			-- 1.3.6.1.4.1.43913.16.8.34.13.2.1.3
			output10GEupgradeStatus OBJECT-TYPE
				SYNTAX UpgradeStatus
				MAX-ACCESS read-only
				STATUS current
				DESCRIPTION
					"The status of upgrade:
					0--	No upgrade performed since boot up,
					1--	Retrieving file,
					2--	Retrieving file failed,
					3--	Updating flash,
					4--	Updating flash failed,
					5--	Updating package error,
					6--	Upgrade complete.
					"
				::= { output10GEupgradeStatusEntry 3 }


			-- 1.3.6.1.4.1.43913.16.8.34.14
			output10GEntpBroadcastConfigTable OBJECT-TYPE
				SYNTAX SEQUENCE OF Output10GEntpBroadcastConfigEntry
				MAX-ACCESS not-accessible
				STATUS current
				DESCRIPTION
					"This table is used to get 10GE output card ntp broadcast config."
				::= { output10GE 14 }

			-- 1.3.6.1.4.1.43913.16.8.34.14.1
			output10GEntpBroadcastConfigEntry OBJECT-TYPE
				SYNTAX Output10GEntpBroadcastConfigEntry
				MAX-ACCESS not-accessible
				STATUS current
				DESCRIPTION
					"The entry of the table."
				INDEX { output10GEntpBroadcastConfigShelfIndex, output10GEntpBroadcastConfigSlotIndex, output10GEntpBroadcastConfigPortIndex }
				::= { output10GEntpBroadcastConfigTable 1 }

			Output10GEntpBroadcastConfigEntry ::=
				SEQUENCE {
					output10GEntpBroadcastConfigShelfIndex
						Integer32,
					output10GEntpBroadcastConfigSlotIndex
						Integer32,
					output10GEntpBroadcastConfigPortIndex
						Integer32,
					output10GEntpBroadcastConfigIp
						DisplayString,
					output10GEntpBroadcastConfigInterval
						Integer32,
					output10GEntpBroadcastConfigState
						Integer32
				}

			-- 1.3.6.1.4.1.43913.1.8.13.7.1.1
			output10GEntpBroadcastConfigShelfIndex OBJECT-TYPE
				SYNTAX Integer32
				MAX-ACCESS read-only
				STATUS current
				DESCRIPTION
					"The shelf index: main(0), exp1(1), exp2(2), exp3(3), exp4(4)."
				::= { output10GEntpBroadcastConfigEntry 1 }

			-- 1.3.6.1.4.1.43913.16.8.34.14.1.2
			output10GEntpBroadcastConfigSlotIndex OBJECT-TYPE
				SYNTAX Integer32
				MAX-ACCESS read-only
				STATUS current
				DESCRIPTION
					"The slot index. When the index is 0(main), the slot-index range is 2~9;
					When the  index is 1~4(exp1~exp4), the slot-index range is 3~14"
				::= { output10GEntpBroadcastConfigEntry 2 }

			-- 1.3.6.1.4.1.43913.16.8.34.14.1.3
			output10GEntpBroadcastConfigPortIndex OBJECT-TYPE
				SYNTAX Integer32
				MAX-ACCESS read-only
				STATUS current
				DESCRIPTION
					"The ptp out card port index. range 0 ~ 3"
				::= { output10GEntpBroadcastConfigEntry 3 }

			-- 1.3.6.1.4.1.43913.16.8.34.14.1.4
			output10GEntpBroadcastConfigIp OBJECT-TYPE
				SYNTAX DisplayString
				MAX-ACCESS read-write
				STATUS current
				DESCRIPTION
					"The ptp out card ntp broadcast ip.
					set format: xxx.xxx.xxx.xxx"
				::= { output10GEntpBroadcastConfigEntry 4 }

			-- 1.3.6.1.4.1.43913.16.8.34.14.1.5
			output10GEntpBroadcastConfigInterval OBJECT-TYPE
				SYNTAX Integer32
				MAX-ACCESS read-write
				STATUS current
				DESCRIPTION
					"The ptp out card ntp broadcast interval.
					set format: x
					x : 4 ~ 17"
				::= { output10GEntpBroadcastConfigEntry 5 }

			-- 1.3.6.1.4.1.43913.16.8.34.14.1.6
			output10GEntpBroadcastConfigState OBJECT-TYPE
				SYNTAX Integer32
				MAX-ACCESS read-write
				STATUS current
				DESCRIPTION
					"The ptp out card ntp broadcast state.
					set format: x
					x : 0-disable,1-enable"
				::= { output10GEntpBroadcastConfigEntry 6 }


			-- 1.3.6.1.4.1.43913.16.8.34.15
			output10GEntpClientMonTable OBJECT-TYPE
				SYNTAX SEQUENCE OF Output10GEntpClientMonEntry
				MAX-ACCESS not-accessible
				STATUS current
				DESCRIPTION
					"This table is used to get 10GE output card ntp client
					mon table."
				::= { output10GE 15 }

			-- 1.3.6.1.4.1.43913.16.8.34.15.1
			output10GEntpClientMonEntry OBJECT-TYPE
				SYNTAX Output10GEntpClientMonEntry
				MAX-ACCESS not-accessible
				STATUS current
				DESCRIPTION
					"The entry of the table."
				INDEX { output10GEntpClientMonShelfIndex, output10GEntpClientMonSlotIndex, output10GEntpClientMonPortIndex,
						output10GEntpClientMonIpIndex }
				::= { output10GEntpClientMonTable 1 }

			Output10GEntpClientMonEntry ::=
				SEQUENCE {
					output10GEntpClientMonShelfIndex
						Integer32,
					output10GEntpClientMonSlotIndex
						Integer32,
					output10GEntpClientMonPortIndex
						Integer32,
					output10GEntpClientMonIpIndex
						Integer32,
					output10GEntpClientMonIp
						DisplayString,
					output10GEntpClientMonThreshold
						Integer32,
					output10GEntpClientMonThresholdExceedStatus
						Integer32
				}

			-- 1.3.6.1.4.1.43913.16.8.34.15.1.1
			output10GEntpClientMonShelfIndex OBJECT-TYPE
				SYNTAX Integer32
				MAX-ACCESS read-only
				STATUS current
				DESCRIPTION
					"The shelf index: main(0), exp1(1), exp2(2), exp3(3), exp4(4)."
				::= { output10GEntpClientMonEntry 1 }

			-- 1.3.6.1.4.1.43913.16.8.34.15.1.2
			output10GEntpClientMonSlotIndex OBJECT-TYPE
				SYNTAX Integer32
				MAX-ACCESS read-only
				STATUS current
				DESCRIPTION
					"The slot index. When the index is 0(main), the slot-index range is 2~9;
					When the  index is 1~4(exp1~exp4), the slot-index range is 3~14."
				::= { output10GEntpClientMonEntry 2 }

			-- 1.3.6.1.4.1.43913.16.8.34.15.1.3
			output10GEntpClientMonPortIndex OBJECT-TYPE
				SYNTAX Integer32
				MAX-ACCESS read-only
				STATUS current
				DESCRIPTION
					"The ptp out card port index. range 0 ~ 3"
				::= { output10GEntpClientMonEntry 3 }

			-- 1.3.6.1.4.1.43913.16.8.34.15.1.4
			output10GEntpClientMonIpIndex OBJECT-TYPE
				SYNTAX Integer32
				MAX-ACCESS read-only
				STATUS current
				DESCRIPTION
					"The ip index. range 0 ~ 9"
				::= { output10GEntpClientMonEntry 4 }

			-- 1.3.6.1.4.1.43913.16.8.34.15.1.5
			output10GEntpClientMonIp OBJECT-TYPE
				SYNTAX DisplayString
				MAX-ACCESS read-write
				STATUS current
				DESCRIPTION
					"Ntp client mon ip.
					set format: xxx.xxx.xxx.xxx"
				::= { output10GEntpClientMonEntry 5 }

			-- 1.3.6.1.4.1.43913.16.8.34.15.1.6
			output10GEntpClientMonThreshold OBJECT-TYPE
				SYNTAX Integer32
				MAX-ACCESS read-write
				STATUS current
				DESCRIPTION
					"Ntp client mon threshold.
					set format: x
					x : 0-not mon, 1 ~ 1000000000ns"
				::= { output10GEntpClientMonEntry 6 }

			-- 1.3.6.1.4.1.43913.16.8.34.15.1.7
			output10GEntpClientMonThresholdExceedStatus OBJECT-TYPE
				SYNTAX Integer32
				MAX-ACCESS read-only
				STATUS current
				DESCRIPTION
					"Ntp client mon threshold exceed status.
					0-not exceed threshold, 1-exceed threshold"
				::= { output10GEntpClientMonEntry 7 }

			-- 1.3.6.1.4.1.43913.16.8.34.16
			output10GEntpClientMon OBJECT IDENTIFIER ::= { output10GE 16 }

			-- 1.3.6.1.4.1.43913.16.8.34.16.1.0
			output10GEntpClientMonIndex OBJECT-TYPE
				SYNTAX DisplayString
				MAX-ACCESS read-write
				STATUS current
				DESCRIPTION
					"Ntp client mon data get index config.
					set format: a,b,c,d;
					a : shelf index(0~4)
					b : slot index(0~14/3~14)
					c : port index(0~3)
					d : ip index(0~9)"
				::= { output10GEntpClientMon 1 }

			-- 1.3.6.1.4.1.43913.16.8.34.16.2.0
			output10GEntpClientMonData OBJECT-TYPE
				SYNTAX DisplayString
				MAX-ACCESS read-only
				STATUS current
				DESCRIPTION
					"Ntp client mon data.
					data total 244 byte,0~3 byte is a unsigned int ipv4 address
					4+(8*i) byte is a double value, i(0~29)"
				::= { output10GEntpClientMon 2 }

			-- 1.3.6.1.4.1.43913.16.8.34.17
			output10GEIpv6ConfigTable OBJECT-TYPE
				SYNTAX SEQUENCE OF Output10GEIpv6ConfigEntry
				MAX-ACCESS not-accessible
				STATUS current
				DESCRIPTION
					"The table of output ptp timestamp delay."
				::={output10GE 17}

			-- 1.3.6.1.4.1.43913.16.8.34.17.1
			output10GEIpv6ConfigEntry OBJECT-TYPE
				SYNTAX  Output10GEIpv6ConfigEntry
				MAX-ACCESS not-accessible
				STATUS current
				DESCRIPTION
					"The entry of output ptp timestamp delay."
				INDEX { output10GEIpv6ConfigShelfIndex, output10GEIpv6ConfigSlotIndex ,output10GEIpv6ConfigPortIndex}
				::={output10GEIpv6ConfigTable 1}

			Output10GEIpv6ConfigEntry ::=
				SEQUENCE{
				output10GEIpv6ConfigShelfIndex
						Integer32,
				output10GEIpv6ConfigSlotIndex
						Integer32,
				output10GEIpv6ConfigPortIndex
						Integer32,
				output10GEIpv6ConfigAddress
						DisplayString
				}

			-- 1.3.6.1.4.1.43913.16.8.34.17.1.1
			output10GEIpv6ConfigShelfIndex OBJECT-TYPE
				SYNTAX Integer32 (0..4)
				MAX-ACCESS not-accessible
				STATUS current
				DESCRIPTION
					"The shelf index: main(0), exp1(1), exp2(2), exp3(3), exp4(4)"
				::={output10GEIpv6ConfigEntry 1}

			-- 1.3.6.1.4.1.43913.16.8.34.17.1.2
			output10GEIpv6ConfigSlotIndex OBJECT-TYPE
				SYNTAX Integer32 (1..14)
				MAX-ACCESS not-accessible
				STATUS current
				DESCRIPTION
					"The slot index. When the index is 0(main), the slot-index range is 2~9;
					When the  index is 1~4(exp1~exp4), the slot-index range is 3~14"
				::={output10GEIpv6ConfigEntry 2}

			-- 1.3.6.1.4.1.43913.16.8.34.17.1.3
			output10GEIpv6ConfigPortIndex OBJECT-TYPE
				SYNTAX Integer32 (1..4)
				MAX-ACCESS not-accessible
				STATUS current
				DESCRIPTION
					"The ptp out card port index. range 0 ~ 3"
				::={output10GEIpv6ConfigEntry 3}

			-- 1.3.6.1.4.1.43913.16.8.34.17.1.4
			output10GEIpv6ConfigAddress OBJECT-TYPE
				SYNTAX DisplayString
				MAX-ACCESS read-write
				STATUS current
				DESCRIPTION
					"Output 10GE card ipv6 address.
					format: xxxx:xxxx:xxxx::xxxx/64"
				::={output10GEIpv6ConfigEntry 4}

			-- 1.3.6.1.4.1.43913.16.8.34.18
			output10GEntpClientMonIpv6Table OBJECT-TYPE
				SYNTAX SEQUENCE OF Output10GEntpClientMonIpv6Entry
				MAX-ACCESS not-accessible
				STATUS current
				DESCRIPTION
					"This table is used to get 10GE output card ntp client
					mon table."
				::= { output10GE 18 }

			-- 1.3.6.1.4.1.43913.16.8.34.18.1
			output10GEntpClientMonIpv6Entry OBJECT-TYPE
				SYNTAX Output10GEntpClientMonIpv6Entry
				MAX-ACCESS not-accessible
				STATUS current
				DESCRIPTION
					"The entry of the table."
				INDEX { output10GEntpClientMonIpv6ShelfIndex, output10GEntpClientMonIpv6SlotIndex,                        output10GEntpClientMonIpv6PortIndex,output10GEntpClientMonIpv6IpIndex }
				::= { output10GEntpClientMonIpv6Table 1 }

			Output10GEntpClientMonIpv6Entry ::=
				SEQUENCE {
					output10GEntpClientMonIpv6ShelfIndex
						Integer32,
					output10GEntpClientMonIpv6SlotIndex
						Integer32,
					output10GEntpClientMonIpv6PortIndex
						Integer32,
					output10GEntpClientMonIpv6IpIndex
						Integer32,
					output10GEntpClientMonIpv6Addr
						DisplayString,
					output10GEntpClientMonIpv6Threshold
						Integer32,
					output10GEntpClientMonIpv6ThresholdExceedStatus
						Integer32
				}

			-- 1.3.6.1.4.1.43913.16.8.34.18.1.1
			output10GEntpClientMonIpv6ShelfIndex OBJECT-TYPE
				SYNTAX Integer32
				MAX-ACCESS read-only
				STATUS current
				DESCRIPTION
					"The shelf index: main(0), exp1(1), exp2(2), exp3(3), exp4(4)."
				::= { output10GEntpClientMonIpv6Entry 1 }

			-- 1.3.6.1.4.1.43913.16.8.34.18.1.2
			output10GEntpClientMonIpv6SlotIndex OBJECT-TYPE
				SYNTAX Integer32
				MAX-ACCESS read-only
				STATUS current
				DESCRIPTION
					"The slot index. When the index is 0(main), the slot-index range is 2~9;
					When the  index is 1~4(exp1~exp4), the slot-index range is 3~14."
				::= { output10GEntpClientMonIpv6Entry 2 }

			-- 1.3.6.1.4.1.43913.16.8.34.18.1.3
			output10GEntpClientMonIpv6PortIndex OBJECT-TYPE
				SYNTAX Integer32
				MAX-ACCESS read-only
				STATUS current
				DESCRIPTION
					"The ptp out card port index. range 0 ~ 3"
				::= { output10GEntpClientMonIpv6Entry 3 }

			-- 1.3.6.1.4.1.43913.16.8.34.18.1.4
			output10GEntpClientMonIpv6IpIndex OBJECT-TYPE
				SYNTAX Integer32
				MAX-ACCESS read-only
				STATUS current
				DESCRIPTION
					"The ip index. range 0 ~ 9"
				::= { output10GEntpClientMonIpv6Entry 4 }

			-- 1.3.6.1.4.1.43913.16.8.34.18.1.5
			output10GEntpClientMonIpv6Addr OBJECT-TYPE
				SYNTAX DisplayString
				MAX-ACCESS read-write
				STATUS current
				DESCRIPTION
					"Ntp client mon ip.
					set format: xxx.xxx.xxx.xxx"
				::= { output10GEntpClientMonIpv6Entry 5 }

			-- 1.3.6.1.4.1.43913.16.8.34.18.1.6
			output10GEntpClientMonIpv6Threshold OBJECT-TYPE
				SYNTAX Integer32
				MAX-ACCESS read-write
				STATUS current
				DESCRIPTION
					"Ntp client mon threshold.
					set format: x
					x : 0-not mon, 1 ~ 1000000000ns"
				::= { output10GEntpClientMonIpv6Entry 6 }

			-- 1.3.6.1.4.1.43913.16.8.34.18.1.7
			output10GEntpClientMonIpv6ThresholdExceedStatus OBJECT-TYPE
				SYNTAX Integer32
				MAX-ACCESS read-only
				STATUS current
				DESCRIPTION
					"Ntp client mon threshold exceed status.
					0-not exceed threshold, 1-exceed threshold"
				::= { output10GEntpClientMonIpv6Entry 7 }


			output10GEntpClientMonIpv6 OBJECT IDENTIFIER ::= { output10GE 19 }

			-- 1.3.6.1.4.1.43913.16.8.34.19.1.0
			output10GEntpClientMonIpv6Index OBJECT-TYPE
				SYNTAX DisplayString
				MAX-ACCESS read-write
				STATUS current
				DESCRIPTION
					"Ntp client mon data get index config.
					set format: a,b,c,d;
					a : shelf index(0~4)
					b : slot index(0~14/3~14)
					c : port index(0~3)
					d : ip index(0~9)"
				::= { output10GEntpClientMonIpv6 1 }

			-- 1.3.6.1.4.1.43913.16.8.34.19.1.1
			output10GEntpClientMonIpv6Data OBJECT-TYPE
				SYNTAX DisplayString
				MAX-ACCESS read-only
				STATUS current
				DESCRIPTION
					"Ntp client mon data.
					data total 244 byte,0~3 byte is a unsigned int ipv4 address
					4+(8*i) byte is a double value, i(0~29)"
				::= { output10GEntpClientMonIpv6 2 }

			-- 1.3.6.1.4.1.43913.16.8.34.20.0
			output10GEcardRedundancy OBJECT-TYPE
				SYNTAX DisplayString
				MAX-ACCESS read-write
				STATUS current
				DESCRIPTION
					"set 10GE out card redundancy state.
					set format: a,b,c,d;
					a : state
					b : 0 ~ 4  (shelf)
					c : 0 ~ 14 (slot)
					d : 0 ~ 1  (enable/disable)
					set 10GE out card get redundancy status index.
					set format: a,b,c,d;
					a : index
					b : 0 ~ 4  (shelf)
					c : 0 ~ 14 (slot)
					d : 0
					get 10GE out card redundancy status.
					get data format: p1;p2;p3;
					p1 format : a,b
					a : 0 ~ 4  (shelf)
					b : 0 ~ 14 (slot)
					p2/p3 format : a,b,c,m1,m2,m3,m4;
					a : 0 ~ 1 (redundancy state, 0-disable, 1-enable)
					b : 0 ~ 1 (redundancy mode, 0-backup, 1-active)
					c : 0 ~ 1 (redundancy peer exist, BIT7-4:number of linkup port, BIT3-0: 1-peer exist, 0-peer not exist)
					m1-4 : port1-4 mac addr
					"
				::= { output10GE 20 }

			--	1.3.6.1.4.1.43913.16.8.34.21.0
			output10GEportRedundancy OBJECT-TYPE
				SYNTAX DisplayString
				MAX-ACCESS read-write
				STATUS current
				DESCRIPTION
					"set 10GE out port redundancy state.
					set format: a,b,c,d,e;
					a : state
					b : 0 ~ 4  (shelf)
					c : 0 ~ 14 (slot)
					d : 0 ~ 1  (port-1-2/port-3-4)
					e : 0 ~ 1  (enable/disable)
					set 10GE out port get redundancy index.
					set format: a,b,c,d,e;
					a : index
					b : 0 ~ 4  (shelf)
					c : 0 ~ 14 (slot)
					d : 0
					e : 0
					get 10GE out port redundancy status.
					get data format: p1;p2;p3;
					p1 format : a,b;
					a : 0 ~ 4  (shelf)
					b : 0 ~ 14 (slot)
					p2/p3 format : a,b
					a : 0 ~ 1   (bonding state)
					b : 0/1/255 (active port/error)
					"
				::= { output10GE 21 }

        -- 1.3.6.1.4.1.43913.16.8.34.22
		output10GEPTPConfigTable OBJECT-TYPE
			SYNTAX SEQUENCE OF Output10GEPTPConfigEntry
			MAX-ACCESS not-accessible
			STATUS current
			DESCRIPTION
				"The table of output ptp card common config info."
			::= {output10GE 22}

	    -- 1.3.6.1.4.1.43913.16.8.34.22.1
		output10GEPTPConfigEntry OBJECT-TYPE
			SYNTAX  Output10GEPTPConfigEntry
			MAX-ACCESS not-accessible
			STATUS current
			DESCRIPTION
				"The entry of output ptp card common config info."
			INDEX { output10GEPTPConfigShelfIndex, output10GEPTPConfigSlotIndex, output10GEPTPConfigPortIndex }
			::= {output10GEPTPConfigTable 1}

		Output10GEPTPConfigEntry ::=
			SEQUENCE{
		       output10GEPTPConfigShelfIndex
		       		Integer32,
		       output10GEPTPConfigSlotIndex
		       		Integer32,
		       output10GEPTPConfigPortIndex
		       		Integer32,
		       output10GEPTPConfigPTPstate
		       		ActionState,
		       output10GEPTPConfigMaxClients
		       		Integer32,
		       output10GEPTPConfigProfile
		       		OutputPTPprofile10GE,
		       output10GEPTPConfigClockID
		       		DisplayString,
		       output10GEPTPConfigPriority1
		       		Integer32,
		       output10GEPTPConfigPriority2
		       		Integer32,
		       output10GEPTPConfigDomain
		       		Integer32,
		       output10GEPTPConfigDSCP
		       		Integer32,
		       output10GEPTPConfigDSCPstate
		       		ActionState,
		       output10GEPTPConfigSyncLimit
		       		Integer32,
		       output10GEPTPConfigAnnounceLimit
		       		Integer32,
		       output10GEPTPConfigDelayLimit
		       		Integer32,
		       output10GEPTPConfigTwoStep
		       		ActionState,
		       output10GEPTPConfigTTL
		       		Integer32,
		       output10GEPTPConfigMgmtAddrMode
		       		Integer32,
		       output10GEPTPConfigAlternateMaster
		       		ActionState,
		       output10GEPTPConfigUnicastNegotiate
		       		ActionState,
		       output10GEPTPConfigUnicastLeaseDuration
		       		Integer32,
		       output10GEPTPConfigDither
		       		Integer32,
		       output10GEPTPConfigServiceMode
		       		PktServiceType
		    }

		-- 1.3.6.1.4.1.43913.16.8.34.22.1.1
		output10GEPTPConfigShelfIndex OBJECT-TYPE
		 	SYNTAX Integer32 (0..4)
		 	MAX-ACCESS not-accessible
		 	STATUS current
		 	DESCRIPTION
		 		"The shelf index: main(0), exp1(1), exp2(2), exp3(3), exp4(4)"
		 	::= {output10GEPTPConfigEntry 1}

      	-- 1.3.6.1.4.1.43913.16.8.34.22.1.2
		output10GEPTPConfigSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::= {output10GEPTPConfigEntry 2}

        -- 1.3.6.1.4.1.43913.16.8.34.22.1.3
		output10GEPTPConfigPortIndex OBJECT-TYPE
		 	SYNTAX Integer32 (1..4)
		 	MAX-ACCESS not-accessible
		 	STATUS current
		 	DESCRIPTION
		 		"The port index. 0~4"
		 	::= {output10GEPTPConfigEntry 3}


		-- 1.3.6.1.4.1.43913.16.8.34.22.1.4
		output10GEPTPConfigPTPstate OBJECT-TYPE
		 	SYNTAX ActionState
		 	MAX-ACCESS read-write
		 	STATUS current
		 	DESCRIPTION
		 		"The state of ptp card"
		 	::= {output10GEPTPConfigEntry 4}

		-- 1.3.6.1.4.1.43913.16.8.34.22.1.5
		output10GEPTPConfigMaxClients OBJECT-TYPE
		 	SYNTAX    Integer32 (1..500)
		 	MAX-ACCESS read-write
		 	STATUS current
		 	DESCRIPTION
		 		"The max client number of ptp card"
		 	::= {output10GEPTPConfigEntry 5}

		-- 1.3.6.1.4.1.43913.16.8.34.22.1.6
		output10GEPTPConfigProfile OBJECT-TYPE
		 	SYNTAX OutputPTPprofile10GE
		 	MAX-ACCESS read-write
		 	STATUS current
		 	DESCRIPTION
		 		"The profile of ptp card. 0: telecom-2008, 1: default, 3: itu-g8265-1, 4: ethernet-default, 6: itu-g8275-1, 9: cm-5G-spec"
		 	::= {output10GEPTPConfigEntry 6}

		 -- 1.3.6.1.4.1.43913.16.8.34.22.1.7
		output10GEPTPConfigClockID OBJECT-TYPE
		 	SYNTAX  DisplayString
		 	MAX-ACCESS read-write
		 	STATUS current
		 	DESCRIPTION
		 		"The clock id of ptp card. in format of MAC address: xx:xx:xx:xx:xx:xx:xx:xx"
		 	::= {output10GEPTPConfigEntry 7}

		-- 1.3.6.1.4.1.43913.16.8.34.22.1.8
		output10GEPTPConfigPriority1 OBJECT-TYPE
		 	SYNTAX    Integer32 (0..255)
		 	MAX-ACCESS read-write
		 	STATUS current
		 	DESCRIPTION
		 		"The priority1 of ptp card. Range: 0~255"
		 	::= {output10GEPTPConfigEntry 8}

		-- 1.3.6.1.4.1.43913.16.8.34.22.1.9
		output10GEPTPConfigPriority2 OBJECT-TYPE
		 	SYNTAX    Integer32 (0..255)
		 	MAX-ACCESS read-write
		 	STATUS current
		 	DESCRIPTION
		 		"The priority2 of ptp card. Range: 0~255"
		 	::= {output10GEPTPConfigEntry 9}

		-- 1.3.6.1.4.1.43913.16.8.34.22.1.10
		output10GEPTPConfigDomain OBJECT-TYPE
		 	SYNTAX   Integer32 (0..255)
		 	MAX-ACCESS read-write
		 	STATUS current
		 	DESCRIPTION
		 		"The domain of ptp card. Range: 0~255"
		 	::= {output10GEPTPConfigEntry 10}

		 -- 1.3.6.1.4.1.43913.16.8.34.22.1.11
		output10GEPTPConfigDSCP OBJECT-TYPE
		 	SYNTAX   Integer32 (0..63)
		 	MAX-ACCESS read-write
		 	STATUS current
		 	DESCRIPTION
		 		"The DSCP number of ptp card. Range: 0~63"
		 	::= {output10GEPTPConfigEntry 11}

		-- 1.3.6.1.4.1.43913.16.8.34.22.1.12
		output10GEPTPConfigDSCPstate OBJECT-TYPE
		 	SYNTAX    ActionState
		 	MAX-ACCESS read-write
		 	STATUS current
		 	DESCRIPTION
		 		"The DSCP enable of ptp card"
		 	::= {output10GEPTPConfigEntry 12}

		-- 1.3.6.1.4.1.43913.16.8.34.22.1.13
		output10GEPTPConfigSyncLimit OBJECT-TYPE
		 	SYNTAX    Integer32 (-7..7)
		 	MAX-ACCESS read-write
		 	STATUS current
		 	DESCRIPTION
		 		"The sync limit of ptp card. Range: -7~7"
		 	::= {output10GEPTPConfigEntry 13}

		-- 1.3.6.1.4.1.43913.16.8.34.22.1.14
		output10GEPTPConfigAnnounceLimit OBJECT-TYPE
		 	SYNTAX   Integer32 (-4..4)
		 	MAX-ACCESS read-write
		 	STATUS current
		 	DESCRIPTION
		 		"The announce limit of ptp card. Range: -4~4"
		 	::= {output10GEPTPConfigEntry 14}

		 -- 1.3.6.1.4.1.43913.16.8.34.22.1.15
		output10GEPTPConfigDelayLimit OBJECT-TYPE
		 	SYNTAX   Integer32 (-7..7)
		 	MAX-ACCESS read-write
		 	STATUS current
		 	DESCRIPTION
		 		"The delay limit of ptp card. Range: -7~7"
		 	::= {output10GEPTPConfigEntry 15}

		-- 1.3.6.1.4.1.43913.16.8.34.22.1.16
		output10GEPTPConfigTwoStep OBJECT-TYPE
		 	SYNTAX  ActionState
		 	MAX-ACCESS read-write
		 	STATUS current
		 	DESCRIPTION
		 		"The two-step enable of ptp card"
		 	::= {output10GEPTPConfigEntry 16}

		-- 1.3.6.1.4.1.43913.16.8.34.22.1.17
		output10GEPTPConfigTTL OBJECT-TYPE
		 	SYNTAX  Integer32 (1..255)
		 	MAX-ACCESS read-write
		 	STATUS current
		 	DESCRIPTION
		 		"The  of ptp card"
		 	::= {output10GEPTPConfigEntry 17}

		-- 1.3.6.1.4.1.43913.16.8.34.22.1.18
		output10GEPTPConfigMgmtAddrMode OBJECT-TYPE
		 	SYNTAX   Integer32 (0..1)
		 	MAX-ACCESS read-write
		 	STATUS current
		 	DESCRIPTION
		 		"The management address mode of ptp card. 0: unicast, 1: multicast"
		 	::= {output10GEPTPConfigEntry 18}

		 -- 1.3.6.1.4.1.43913.16.8.34.22.1.19
		output10GEPTPConfigAlternateMaster OBJECT-TYPE
		 	SYNTAX   ActionState
		 	MAX-ACCESS read-write
		 	STATUS current
		 	DESCRIPTION
		 		"The alternate master enable of ptp card"
		 	::= {output10GEPTPConfigEntry 19}

		-- 1.3.6.1.4.1.43913.16.8.34.22.1.20
		output10GEPTPConfigUnicastNegotiate OBJECT-TYPE
		 	SYNTAX    ActionState
		 	MAX-ACCESS read-write
		 	STATUS current
		 	DESCRIPTION
		 		"The unicast negotiate enable of ptp card"
		 	::= {output10GEPTPConfigEntry 20}

		-- 1.3.6.1.4.1.43913.16.8.34.22.1.21
		output10GEPTPConfigUnicastLeaseDuration OBJECT-TYPE
		 	SYNTAX     Integer32 (10..1000)
		 	MAX-ACCESS read-write
		 	STATUS current
		 	DESCRIPTION
		 		"The unicast lease duration of ptp card. Range: 10~1000"
		 	::= {output10GEPTPConfigEntry 21}

		-- 1.3.6.1.4.1.43913.16.8.34.22.1.22
		output10GEPTPConfigDither OBJECT-TYPE
		 	SYNTAX     Integer32 (0..1)
		 	MAX-ACCESS read-write
		 	STATUS current
		 	DESCRIPTION
		 		"The Dither state of ptp output card: enable(1), disable(0)"
		 	::= {output10GEPTPConfigEntry 22}

		-- 1.3.6.1.4.1.43913.16.8.34.22.1.23
		output10GEPTPConfigServiceMode OBJECT-TYPE
		 	SYNTAX     PktServiceType
		 	MAX-ACCESS read-write
		 	STATUS current
		 	DESCRIPTION
		 		"The service type: 0-ptp_gm  1-ptp_probe  2-ntp_server  3-ntp_probe"
		 	::= {output10GEPTPConfigEntry 23}

		-- 1.3.6.1.4.1.43913.16.8.34.23
		output10GEPTPStatusTable OBJECT-TYPE
			SYNTAX SEQUENCE OF Output10GEPTPStatusEntry
			MAX-ACCESS not-accessible
			STATUS current
			DESCRIPTION
				"The table of output ptp status info."
			::={output10GE 23}

        -- 1.3.6.1.4.1.43913.16.8.34.23.1
		output10GEPTPStatusEntry OBJECT-TYPE
			SYNTAX  Output10GEPTPStatusEntry
			MAX-ACCESS not-accessible
			STATUS current
			DESCRIPTION
				"The entry of output ptpstatus info."
			INDEX { output10GEPTPStatusShelfIndex, output10GEPTPStatusSlotIndex, output10GEPTPStatusPortIndex }
			::={output10GEPTPStatusTable 1}

		Output10GEPTPStatusEntry ::=
			SEQUENCE{
		       output10GEPTPStatusShelfIndex
		       		Integer32,
		       output10GEPTPStatusSlotIndex
		       		Integer32,
		       output10GEPTPStatusPortIndex
		       		Integer32,
		       output10GEPTPStatusPortEnabled
					DisplayString,
				output10GEPTPStatusClockID
					DisplayString,
				output10GEPTPStatusProfile
					DisplayString,
				output10GEPTPStatusPortState
					DisplayString,
				output10GEPTPStatusClockClass
					DisplayString,
				output10GEPTPStatusClockAccuracy
					DisplayString,
				output10GEPTPStatusTimescale
					DisplayString,
				output10GEPTPStatusClientNum
					DisplayString,
				output10GEPTPStatusClientLoad
					DisplayString
              }

        -- 1.3.6.1.4.1.43913.16.8.34.23.1.1
		output10GEPTPStatusShelfIndex OBJECT-TYPE
		 	SYNTAX Integer32 (0..4)
		 	MAX-ACCESS not-accessible
		 	STATUS current
		 	DESCRIPTION
		 		"The shelf index: main(0), exp1(1), exp2(2), exp3(3), exp4(4)"
		 	::={output10GEPTPStatusEntry 1}

	    -- 1.3.6.1.4.1.43913.16.8.34.23.1.2
		output10GEPTPStatusSlotIndex OBJECT-TYPE
		 	SYNTAX Integer32 (0..14)
		 	MAX-ACCESS not-accessible
		 	STATUS current
		 	DESCRIPTION
		 		"The slot index. When the index is 0(main), the slot-index range is 2~9;
		 		 When the  index is 1~4(exp1~exp4), the slot-index range is 3~14"
		 	::={output10GEPTPStatusEntry 2}

		-- 1.3.6.1.4.1.43913.16.8.34.23.1.3
		output10GEPTPStatusPortIndex OBJECT-TYPE
		 	SYNTAX Integer32 (1..4)
		 	MAX-ACCESS not-accessible
		 	STATUS current
		 	DESCRIPTION
		 		"The port index. port1~port4"
		 	::={output10GEPTPStatusEntry 3 }

		-- 1.3.6.1.4.1.43913.16.8.34.23.1.4
		output10GEPTPStatusPortEnabled OBJECT-TYPE
			SYNTAX DisplayString
			MAX-ACCESS read-only
			STATUS current
			DESCRIPTION
				"The PTP port state control flag."
			::= { output10GEPTPStatusEntry 4 }


		-- 1.3.6.1.4.1.43913.16.8.34.23.1.5
		output10GEPTPStatusClockID OBJECT-TYPE
			SYNTAX DisplayString
			MAX-ACCESS read-only
			STATUS current
			DESCRIPTION
				"The clock ID of a PTP port."
			::= { output10GEPTPStatusEntry 5 }


		-- 1.3.6.1.4.1.43913.16.8.34.23.1.6
		output10GEPTPStatusProfile OBJECT-TYPE
			SYNTAX DisplayString
			MAX-ACCESS read-only
			STATUS current
			DESCRIPTION
				"PTP common profile."
			::= { output10GEPTPStatusEntry 6 }


		-- 1.3.6.1.4.1.43913.16.8.34.23.1.7
		output10GEPTPStatusPortState OBJECT-TYPE
			SYNTAX DisplayString
			MAX-ACCESS read-only
			STATUS current
			DESCRIPTION
				"PTP port state."
			::= { output10GEPTPStatusEntry 7 }


		-- 1.3.6.1.4.1.43913.16.8.34.23.1.8
		output10GEPTPStatusClockClass OBJECT-TYPE
			SYNTAX DisplayString
			MAX-ACCESS read-only
			STATUS current
			DESCRIPTION
				"The clock class on a PTP port."
			::= { output10GEPTPStatusEntry 8 }


		-- 1.3.6.1.4.1.43913.16.8.34.23.1.9
		output10GEPTPStatusClockAccuracy OBJECT-TYPE
			SYNTAX DisplayString
			MAX-ACCESS read-only
			STATUS current
			DESCRIPTION
				"The clock accuracy on a PTP port."
			::= { output10GEPTPStatusEntry 9 }


		-- 1.3.6.1.4.1.43913.16.8.34.23.1.10
		output10GEPTPStatusTimescale OBJECT-TYPE
			SYNTAX DisplayString
			MAX-ACCESS read-only
			STATUS current
			DESCRIPTION
				"The timescale on a PTP port."
			::= { output10GEPTPStatusEntry 10 }


		-- 1.3.6.1.4.1.43913.16.8.34.23.1.11
		output10GEPTPStatusClientNum OBJECT-TYPE
			SYNTAX DisplayString
			MAX-ACCESS read-only
			STATUS current
			DESCRIPTION
				"The number of clients on a PTP port."
			::= { output10GEPTPStatusEntry 11 }


		-- 1.3.6.1.4.1.43913.16.8.34.23.1.12
		output10GEPTPStatusClientLoad OBJECT-TYPE
			SYNTAX DisplayString
			MAX-ACCESS read-only
			STATUS current
			DESCRIPTION
				"The percentage of client load on a PTP port."
			::= { output10GEPTPStatusEntry 12 }

		-- 1.3.6.1.4.1.43913.16.8.35
		outputFiberTable OBJECT-TYPE
			SYNTAX SEQUENCE OF OutputFiberEntry
			MAX-ACCESS not-accessible
			STATUS current
			DESCRIPTION
				"The table of fiber config."
			::= {inputOutput 35}

	    -- 1.3.6.1.4.1.43913.16.8.11.1
		outputFiberEntry OBJECT-TYPE
			SYNTAX  OutputFiberEntry
			MAX-ACCESS not-accessible
			STATUS current
			DESCRIPTION
				"The entry of fiber config."
			INDEX { outputFiberIndex, outputFiberSlotIndex }
			::= {outputFiberTable 1}

		OutputFiberEntry ::=
			SEQUENCE{
				outputFiberIndex
					Integer32,
				outputFiberSlotIndex
					Integer32,
				outputFiberState
					ActionState
			}

		 -- 1.3.6.1.4.1.43913.16.8.11.1.1
		 outputFiberIndex OBJECT-TYPE
		 	SYNTAX Integer32 (0..4)
		 	MAX-ACCESS not-accessible
		 	STATUS current
		 	DESCRIPTION
		 		"The fiber index: main(0), exp1(1), exp2(2), exp3(3), exp4(4)"
		 	::= {outputFiberEntry 1}

		-- 1.3.6.1.4.1.43913.16.8.11.1.2
		outputFiberSlotIndex OBJECT-TYPE
			SYNTAX Integer32 (1..14)
		 	MAX-ACCESS not-accessible
		 	STATUS current
		 	DESCRIPTION
		 		"The fiber slot index. When the pps-tod index is 0(main), the slot-index range is 1~9;
		 		 When the fiber index is 1~4(exp1~exp4), the slot-index range is 3~14"
		 	::= {outputFiberEntry 2}

		-- 1.3.6.1.4.1.43913.16.8.11.1.3
		outputFiberState OBJECT-TYPE
			SYNTAX ActionState
		 	MAX-ACCESS read-write
		 	STATUS current
		 	DESCRIPTION
		 		"Show / Set the state of fiber"
		 	::= {outputFiberEntry 3}

		-- 1.3.6.1.4.1.43913.16.10
		network OBJECT IDENTIFIER ::= { sm2000-5g 10 }

		-- 1.3.6.1.4.1.43913.16.10.1
		hostname OBJECT-TYPE
			SYNTAX DisplayString
			MAX-ACCESS read-write
			STATUS current
			DESCRIPTION
				"The system hostname of SM2000-5G device."
			::= { network 1 }


		-- 1.3.6.1.4.1.43913.16.10.2
		ipMCMode OBJECT-TYPE
			SYNTAX IpMCMode
			MAX-ACCESS read-write
			STATUS current
			DESCRIPTION
				"Show / Set IP mode of MC board, static(0), dhcp(1)"
			::= { network 2 }


		-- 1.3.6.1.4.1.43913.16.10.3
		firewallTable OBJECT-TYPE
			SYNTAX SEQUENCE OF FirewallEntry
			MAX-ACCESS not-accessible
			STATUS current
			DESCRIPTION
				"The firewall table of MC module of SM2000-5G device."
			::= { network 3 }


		-- 1.3.6.1.4.1.43913.16.10.3.1
		firewallEntry OBJECT-TYPE
			SYNTAX FirewallEntry
			MAX-ACCESS not-accessible
			STATUS current
			DESCRIPTION
				"The entry of MC firewall table."
			INDEX { firewallIndex }
			::= { firewallTable 1 }


		FirewallEntry ::=
			SEQUENCE {
				firewallIndex
					Integer32,
				firewallType
					FirewallType,
				firewallState
					FirewallState
			 }

		-- 1.3.6.1.4.1.43913.16.10.3.1.1
		firewallIndex OBJECT-TYPE
			SYNTAX Integer32 (1..6)
			MAX-ACCESS not-accessible
			STATUS current
			DESCRIPTION
				"The MC firewall index."
			::= { firewallEntry 1 }


		-- 1.3.6.1.4.1.43913.16.10.3.1.2
		firewallType OBJECT-TYPE
			SYNTAX FirewallType
			MAX-ACCESS read-only
			STATUS current
			DESCRIPTION
				"Firewall type."
			::= { firewallEntry 2 }


		-- 1.3.6.1.4.1.43913.16.10.3.1.3
		firewallState OBJECT-TYPE
			SYNTAX FirewallState
			MAX-ACCESS read-write
			STATUS current
			DESCRIPTION
				"Firewall state. The setting could be block(0), or allow(1)."
			::= { firewallEntry 3 }


		-- 1.3.6.1.4.1.43913.16.10.6
		ip OBJECT IDENTIFIER ::= { network 6 }


		-- 1.3.6.1.4.1.43913.16.10.6.1
		ipStatusTable OBJECT-TYPE
			SYNTAX SEQUENCE OF IpStatusEntry
			MAX-ACCESS not-accessible
			STATUS current
			DESCRIPTION
				"IP status table."
			::= { ip 1 }


		-- 1.3.6.1.4.1.43913.16.10.6.1.1
		ipStatusEntry OBJECT-TYPE
			SYNTAX IpStatusEntry
			MAX-ACCESS not-accessible
			STATUS current
			DESCRIPTION
				"The entry of IP status table."
			INDEX { ipStatusIndex }
			::= { ipStatusTable 1 }


		IpStatusEntry ::=
			SEQUENCE {
				ipStatusIndex
					Integer32,
				ipStatusModuleID
					DisplayString,
				ipStatusPortID
					DisplayString,
				ipStatusHWAddr
					DisplayString,
				ipStatusNetInfo
					DisplayString,
				ipStatusOtherInfo
					DisplayString
			 }

		-- 1.3.6.1.4.1.43913.16.10.6.1.1.1
		ipStatusIndex OBJECT-TYPE
			SYNTAX Integer32 (1..96)
			MAX-ACCESS not-accessible
			STATUS current
			DESCRIPTION
				"The index of IP status table."
			::= { ipStatusEntry 1 }


		-- 1.3.6.1.4.1.43913.16.10.6.1.1.2
		ipStatusModuleID OBJECT-TYPE
			SYNTAX DisplayString
			MAX-ACCESS read-only
			STATUS current
			DESCRIPTION
				"It should be MC, CC1 or CC2."
			::= { ipStatusEntry 2 }


		-- 1.3.6.1.4.1.43913.16.10.6.1.1.3
		ipStatusPortID OBJECT-TYPE
			SYNTAX DisplayString
			MAX-ACCESS read-only
			STATUS current
			DESCRIPTION
				"IP port ID."
			::= { ipStatusEntry 3 }


		-- 1.3.6.1.4.1.43913.16.10.6.1.1.4
		ipStatusHWAddr OBJECT-TYPE
			SYNTAX DisplayString
			MAX-ACCESS read-only
			STATUS current
			DESCRIPTION
				"HW address, type and other info of an ethernet port."
			::= { ipStatusEntry 4 }


		-- 1.3.6.1.4.1.43913.16.10.6.1.1.5
		ipStatusNetInfo OBJECT-TYPE
			SYNTAX DisplayString
			MAX-ACCESS read-only
			STATUS current
			DESCRIPTION
				"IP address, mask, gateway and other info of an ethernet port."
			::= { ipStatusEntry 5 }


		-- 1.3.6.1.4.1.43913.16.10.6.1.1.6
		ipStatusOtherInfo OBJECT-TYPE
			SYNTAX DisplayString
			MAX-ACCESS read-only
			STATUS current
			DESCRIPTION
				"Other operational status of an ethernet port."
			::= { ipStatusEntry 6 }


		-- 1.3.6.1.4.1.43913.16.10.6.2
		ipConfigTable OBJECT-TYPE
			SYNTAX SEQUENCE OF IpConfigEntry
			MAX-ACCESS not-accessible
			STATUS current
			DESCRIPTION
				"The IP port configuration table."
			::= { ip 2 }


		-- 1.3.6.1.4.1.43913.16.10.6.2.1
		ipConfigEntry OBJECT-TYPE
			SYNTAX IpConfigEntry
			MAX-ACCESS not-accessible
			STATUS current
			DESCRIPTION
				"The entry of IP port configuration table."
			INDEX { ipConfigIndex }
			::= { ipConfigTable 1 }


		IpConfigEntry ::=
			SEQUENCE {
				ipConfigIndex
					Integer32,
				ipModuleID
					DisplayString,
				ipPortID
					DisplayString,
				ipAddress
					DisplayString,
				ipPortState
					IpPortState,
				ipv6Address
					DisplayString
			 }

		-- 1.3.6.1.4.1.43913.16.10.6.2.1.1
		ipConfigIndex OBJECT-TYPE
			SYNTAX Integer32 (1..5)
			MAX-ACCESS not-accessible
			STATUS current
			DESCRIPTION
				"The index of IP port configuration table."
			::= { ipConfigEntry 1 }


		-- 1.3.6.1.4.1.43913.16.10.6.2.1.2
		ipModuleID OBJECT-TYPE
			SYNTAX DisplayString
			MAX-ACCESS read-only
			STATUS current
			DESCRIPTION
				"It should be MC, CC1 or CC2."
			::= { ipConfigEntry 2 }


		-- 1.3.6.1.4.1.43913.16.10.6.2.1.3
		ipPortID OBJECT-TYPE
			SYNTAX DisplayString
			MAX-ACCESS read-only
			STATUS current
			DESCRIPTION
				"It should be MGMT, ETH1 or ETH2."
			::= { ipConfigEntry 3 }


		-- 1.3.6.1.4.1.43913.16.10.6.2.1.4
		ipAddress OBJECT-TYPE
			SYNTAX DisplayString
			MAX-ACCESS read-write
			STATUS current
			DESCRIPTION
				"The address of the IP port of each board. The format is : address,netmask,gateway. After changing value, user must restart interface by setting ipPortState to restart in ipPortTable."
			::= { ipConfigEntry 4 }


		-- 1.3.6.1.4.1.43913.16.10.6.2.1.5
		ipPortState OBJECT-TYPE
			SYNTAX IpPortState
			MAX-ACCESS read-write
			STATUS current
			DESCRIPTION
				"The state of an IP port. The definition is as follows: disable(0), enable(1), restart(2)."
			::= { ipConfigEntry 5 }


		-- 1.3.6.1.4.1.43913.16.10.6.2.1.6
		ipv6Address OBJECT-TYPE
			SYNTAX DisplayString
			MAX-ACCESS read-write
			STATUS current
			DESCRIPTION
				"The address of the IP port of each board. The format is : xxxx:xxxx:xxxx::xxxx/64. After changing value, user must restart interface by setting ipPortState to restart in ipPortTable."
			::= { ipConfigEntry 6 }


		-- 1.3.6.1.4.1.43913.16.10.7
		eth OBJECT IDENTIFIER ::= { network 7 }


		-- 1.3.6.1.4.1.43913.16.10.7.1
		ethLinkTable OBJECT-TYPE
			SYNTAX SEQUENCE OF EthLinkEntry
			MAX-ACCESS not-accessible
			STATUS current
			DESCRIPTION
				"The Ethernet port link table of the SM2000-5G device."
			::= { eth 1 }


		-- 1.3.6.1.4.1.43913.16.10.7.1.1
		ethLinkEntry OBJECT-TYPE
			SYNTAX EthLinkEntry
			MAX-ACCESS not-accessible
			STATUS current
			DESCRIPTION
				"The ethernet link table."
			INDEX { ethLinkIndex }
			::= { ethLinkTable 1 }


		EthLinkEntry ::=
			SEQUENCE {
				ethLinkIndex
					Integer32,
				ethLinkModuleID
					DisplayString,
				ethLinkPortID
					Integer32,
				ethLinkSpeed
					CurrentEthLinkSpeed
			 }

		-- 1.3.6.1.4.1.43913.16.10.7.1.1.1
		ethLinkIndex OBJECT-TYPE
			SYNTAX Integer32 (1..4)
			MAX-ACCESS not-accessible
			STATUS current
			DESCRIPTION
				"The index of ethernet link table."
			::= { ethLinkEntry 1 }


		-- 1.3.6.1.4.1.43913.16.10.7.1.1.2
		ethLinkModuleID OBJECT-TYPE
			SYNTAX DisplayString
			MAX-ACCESS read-only
			STATUS current
			DESCRIPTION
				"The module ID of SM2000-5G boards. The module is as follows: CC1, CC2."
			::= { ethLinkEntry 2 }


		-- 1.3.6.1.4.1.43913.16.10.7.1.1.3
		ethLinkPortID OBJECT-TYPE
			SYNTAX Integer32
			MAX-ACCESS read-only
			STATUS current
			DESCRIPTION
				"IP Port ID on each board. The value should be one of 1, 2."
			::= { ethLinkEntry 3 }


		-- 1.3.6.1.4.1.43913.16.10.7.1.1.4
		ethLinkSpeed OBJECT-TYPE
			SYNTAX CurrentEthLinkSpeed
			MAX-ACCESS read-only
			STATUS current
			DESCRIPTION
				"The ethernet auto-negotiation speed. The defined speeds are 100M(1), 1000M(2), or none(0)."
			::= { ethLinkEntry 4 }


		-- 1.3.6.1.4.1.43913.16.10.7.2
		ethAutoNegTable OBJECT-TYPE
			SYNTAX SEQUENCE OF EthAutoNegEntry
			MAX-ACCESS not-accessible
			STATUS current
			DESCRIPTION
				"The IP port auto-negotiation table of SM2000-5G device."
			::= { eth 2 }


		-- 1.3.6.1.4.1.43913.16.10.7.2.1
		ethAutoNegEntry OBJECT-TYPE
			SYNTAX EthAutoNegEntry
			MAX-ACCESS not-accessible
			STATUS current
			DESCRIPTION
				"The ethernet auto-negotiation table."
			INDEX { ethAutoNegIndex }
			::= { ethAutoNegTable 1 }


		EthAutoNegEntry ::=
			SEQUENCE {
				ethAutoNegIndex
					Integer32,
				ethAutoNegModuleID
					DisplayString,
				ethAutoNegPortID
					Integer32,
				ethAutoNegSpeed
					CCethLinkSpeedCfg,
				ethAutoNegState
					ActionState
			 }

		-- 1.3.6.1.4.1.43913.16.10.7.2.1.1
		ethAutoNegIndex OBJECT-TYPE
			SYNTAX Integer32 (1..4)
			MAX-ACCESS not-accessible
			STATUS current
			DESCRIPTION
				"The index of ethernet auto-negotiation table."
			::= { ethAutoNegEntry 1 }


		-- 1.3.6.1.4.1.43913.16.10.7.2.1.2
		ethAutoNegModuleID OBJECT-TYPE
			SYNTAX DisplayString
			MAX-ACCESS read-only
			STATUS current
			DESCRIPTION
				"The module ID of SM2000-5G boards. The module is as follows: CC1, CC2."
			::= { ethAutoNegEntry 2 }


		-- 1.3.6.1.4.1.43913.16.10.7.2.1.3
		ethAutoNegPortID OBJECT-TYPE
			SYNTAX Integer32
			MAX-ACCESS read-only
			STATUS current
			DESCRIPTION
				"IP Port ID on each board. The value should be one of 1, 2."
			::= { ethAutoNegEntry 3 }


		-- 1.3.6.1.4.1.43913.16.10.7.2.1.4
		ethAutoNegSpeed OBJECT-TYPE
			SYNTAX CCethLinkSpeedCfg
			MAX-ACCESS read-write
			STATUS current
			DESCRIPTION
				"The ethernet auto-negotiation advertised speed. The defined speeds are 100M(1), 1000M(2), all(0)."
			::= { ethAutoNegEntry 4 }


		-- 1.3.6.1.4.1.43913.16.10.7.2.1.5
		ethAutoNegState OBJECT-TYPE
			SYNTAX ActionState
			MAX-ACCESS read-write
			STATUS current
			DESCRIPTION
				"The IP port auto-negotiation state. The definition is as follows: enable(1), disable(0)."
			::= { ethAutoNegEntry 5 }


		-- 1.3.6.1.4.1.43913.16.10.8
		vlan OBJECT IDENTIFIER ::= { network 8 }


		-- 1.3.6.1.4.1.43913.16.10.8.1
		deletePort1StaticVlan OBJECT-TYPE
			SYNTAX Integer32
			MAX-ACCESS read-write
			STATUS current
			DESCRIPTION
				"To delete static VLAN of port 1, the parameter is VLAN table index."
			::= { vlan 1 }


		-- 1.3.6.1.4.1.43913.16.10.8.2
		deletePort2StaticVlan OBJECT-TYPE
			SYNTAX Integer32
			MAX-ACCESS read-write
			STATUS current
			DESCRIPTION
				"To delete static VLAN of port 2, the parameter is VLAN table index."
			::= { vlan 2 }


		-- 1.3.6.1.4.1.43913.16.10.8.3
		deletePort1DynamicVlan OBJECT-TYPE
			SYNTAX Integer32
			MAX-ACCESS read-write
			STATUS current
			DESCRIPTION
				"To delete dynamic VLAN of port 1, the parameter is VLAN ID."
			::= { vlan 3 }


		-- 1.3.6.1.4.1.43913.16.10.8.4
		deletePort2DynamicVlan OBJECT-TYPE
			SYNTAX Integer32
			MAX-ACCESS read-write
			STATUS current
			DESCRIPTION
				"To delete dynamic VLAN of port 2, the parameter is VLAN ID."
			::= { vlan 4 }


		-- 1.3.6.1.4.1.43913.16.10.8.5
		vlanModeTable OBJECT-TYPE
			SYNTAX SEQUENCE OF VlanModeEntry
			MAX-ACCESS not-accessible
			STATUS current
			DESCRIPTION
				"The VLAN mode table of SM2000-5G device. Controls overall VLAN enable for each port."
			::= { vlan 5 }


		-- 1.3.6.1.4.1.43913.16.10.8.5.1
		vlanModeEntry OBJECT-TYPE
			SYNTAX VlanModeEntry
			MAX-ACCESS not-accessible
			STATUS current
			DESCRIPTION
				"The VLAN mode table entry."
			INDEX { vlanModeIndex }
			::= { vlanModeTable 1 }


		VlanModeEntry ::=
			SEQUENCE {
				vlanModeIndex
					Integer32,
				vlanModeModuleID
					DisplayString,
				vlanModePortID
					Integer32,
				vlanModePortState
					ActionState
			 }

		-- 1.3.6.1.4.1.43913.16.10.8.5.1.1
		vlanModeIndex OBJECT-TYPE
			SYNTAX Integer32 (1..2)
			MAX-ACCESS not-accessible
			STATUS current
			DESCRIPTION
				"The index of VLAN mode table."
			::= { vlanModeEntry 1 }


		-- 1.3.6.1.4.1.43913.16.10.8.5.1.2
		vlanModeModuleID OBJECT-TYPE
			SYNTAX DisplayString
			MAX-ACCESS read-only
			STATUS current
			DESCRIPTION
				"The VLAN module ID. The valid ID should be one of CC1 or CC2."
			::= { vlanModeEntry 2 }


		-- 1.3.6.1.4.1.43913.16.10.8.5.1.3
		vlanModePortID OBJECT-TYPE
			SYNTAX Integer32
			MAX-ACCESS read-only
			STATUS current
			DESCRIPTION
				"The Ethernet Port ID on CC board. The port definition is as follows: 1, 2."
			::= { vlanModeEntry 3 }


		-- 1.3.6.1.4.1.43913.16.10.8.5.1.4
		vlanModePortState OBJECT-TYPE
			SYNTAX ActionState
			MAX-ACCESS read-write
			STATUS current
			DESCRIPTION
				"The VLAN state of CC port. The definition is as follows: enable(1), disable(0)."
			::= { vlanModeEntry 4 }


		-- 1.3.6.1.4.1.43913.16.10.8.6
		vlanTable OBJECT-TYPE
			SYNTAX SEQUENCE OF VlanEntry
			MAX-ACCESS not-accessible
			STATUS current
			DESCRIPTION
				"The VLAN table of SM2000-5G device."
			::= { vlan 6 }


		-- 1.3.6.1.4.1.43913.16.10.8.6.1
		vlanEntry OBJECT-TYPE
			SYNTAX VlanEntry
			MAX-ACCESS not-accessible
			STATUS current
			DESCRIPTION
				"The VLAN table entry."
			INDEX { vlanIndex }
			::= { vlanTable 1 }


		VlanEntry ::=
			SEQUENCE {
				vlanIndex
					Integer32,
				vlanModuleID
					DisplayString,
				vlanPortID
					Integer32,
				vlanState
					ActionState,
				vlanCfg
					DisplayString
			 }

		-- 1.3.6.1.4.1.43913.16.10.8.6.1.1
		vlanIndex OBJECT-TYPE
			SYNTAX Integer32 (1..32)
			MAX-ACCESS not-accessible
			STATUS current
			DESCRIPTION
				"The index of VLAN table."
			::= { vlanEntry 1 }


		-- 1.3.6.1.4.1.43913.16.10.8.6.1.2
		vlanModuleID OBJECT-TYPE
			SYNTAX DisplayString
			MAX-ACCESS read-only
			STATUS current
			DESCRIPTION
				"The vlan module ID. The valid ID should be one of CC1 or CC2."
			::= { vlanEntry 2 }


		-- 1.3.6.1.4.1.43913.16.10.8.6.1.3
		vlanPortID OBJECT-TYPE
			SYNTAX Integer32
			MAX-ACCESS read-only
			STATUS current
			DESCRIPTION
				"The Ethernet Port ID on CC board. The detailed definition is as follows: 1, 2."
			::= { vlanEntry 3 }


		-- 1.3.6.1.4.1.43913.16.10.8.6.1.4
		vlanState OBJECT-TYPE
			SYNTAX ActionState
			MAX-ACCESS read-write
			STATUS current
			DESCRIPTION
				"The state for this vlan index. The state definition is as follows: enable(1), disable(0)."
			::= { vlanEntry 4 }


		-- 1.3.6.1.4.1.43913.16.10.8.6.1.5
		vlanCfg OBJECT-TYPE
			SYNTAX DisplayString
			MAX-ACCESS read-write
			STATUS current
			DESCRIPTION
				"VLAN config information. There are 2 configraion formats, (1)for fix; (2)for dynamic :
				Add:
					1) index=2,id=5,priority=5,addr=192.168.2.222,netmask=255.255.255.0,gateway=192.168.2.1
					2) id=1,priority=3,addr=192.168.2.200,netmask=255.255.255.0,nextHop=192.168.2.1,destNetwork=192.168.2.0/24
				Modify:
					1) addr=192.168.2.222,netmask=255.255.255.0,gateway=192.168.2.1
					2) addr=192.168.2.200,netmask=255.255.255.0,nextHop=192.168.2.1,destNetwork=192.168.2.0/24
				Delete:
					1) delete-index=5
					2) delete-vlanid=5
				"
			::= { vlanEntry 5 }

		-- 1.3.6.1.4.1.43913.16.10.9
		accessControl OBJECT IDENTIFIER ::= { network 9 }

		-- 1.3.6.1.4.1.43913.16.10.9.1
		accessList OBJECT IDENTIFIER ::= { accessControl 1 }

		-- 1.3.6.1.4.1.43913.16.10.9.1.1
		groupLimit OBJECT-TYPE
			SYNTAX Integer32 (1..100)
			MAX-ACCESS read-write
			STATUS current
			DESCRIPTION
				"Show / Set group-limit ."
			::= { accessList 1 }

		-- 1.3.6.1.4.1.43913.16.10.9.1.2
		rowLimit OBJECT-TYPE
			SYNTAX Integer32 (1..1000)
			MAX-ACCESS read-write
			STATUS current
			DESCRIPTION
				"Show / Set row-limit ."
			::= { accessList 2 }

		-- 1.3.6.1.4.1.43913.16.10.9.1.3
		aclInfoTable OBJECT-TYPE
			SYNTAX SEQUENCE OF AclInfoEntry
			MAX-ACCESS not-accessible
			STATUS current
			DESCRIPTION
				"The table views the acl-info."
			::= { accessList 3 }

		-- 1.3.6.1.4.1.43913.16.10.9.1.3.1
		aclInfoEntry OBJECT-TYPE
			SYNTAX AclInfoEntry
			MAX-ACCESS not-accessible
			STATUS current
			DESCRIPTION
				"The entry of acl-info table."
			INDEX { aclInfoIndex }
			::= { aclInfoTable 1 }

		AclInfoEntry ::=
			SEQUENCE {
				aclInfoIndex
					Integer32,
				aclNo
					Integer32,
				aclRules
					Integer32,
				aclType
					DisplayString
			 }

		-- 1.3.6.1.4.1.43913.16.10.9.1.3.1.1
		aclInfoIndex OBJECT-TYPE
			SYNTAX Integer32 (1..20)
			MAX-ACCESS not-accessible
			STATUS current
			DESCRIPTION
				"The index of acl-info table."
			::= { aclInfoEntry 1 }

		-- 1.3.6.1.4.1.43913.16.10.9.1.3.1.2
		aclNo OBJECT-TYPE
			SYNTAX Integer32
			MAX-ACCESS read-only
			STATUS current
			DESCRIPTION
				"The number of group for the acl."
			::= { aclInfoEntry 2 }

		-- 1.3.6.1.4.1.43913.16.10.9.1.3.1.3
		aclRules OBJECT-TYPE
			SYNTAX Integer32
			MAX-ACCESS read-only
			STATUS current
			DESCRIPTION
				"The number of rules for the index."
			::= { aclInfoEntry 3 }

		-- 1.3.6.1.4.1.43913.16.10.9.1.3.1.4
		aclType OBJECT-TYPE
			SYNTAX DisplayString
			MAX-ACCESS read-only
			STATUS current
			DESCRIPTION
				"The type of group for the index. Include ipv4,ipv6 and ethernet."
			::= { aclInfoEntry 4 }

		-- 1.3.6.1.4.1.43913.16.10.9.1.4
		aclNoClearAll OBJECT-TYPE
			SYNTAX Integer32 (1..100)
			MAX-ACCESS read-write
			STATUS current
			DESCRIPTION
				"Clear the access-list-number config .Enter the acl-no to be cleared."
			::= { accessList 4 }

		-- 1.3.6.1.4.1.43913.16.10.9.1.5
		chooseAclNum OBJECT-TYPE
			SYNTAX Integer32 (1..100)
			MAX-ACCESS read-write
			STATUS current
			DESCRIPTION
				"The value affects the viewing of the aclConfigTable."
			::= { accessList 5 }

		-- 1.3.6.1.4.1.43913.16.10.9.1.6
		aclConfigTable OBJECT-TYPE
			SYNTAX SEQUENCE OF AclConfigEntry
			MAX-ACCESS not-accessible
			STATUS current
			DESCRIPTION
				"The table is the access-list configuration of the chooseAclNum.
				 Please enter the chooseAclNum before viewing the aclConfigTable."
			::= { accessList 6 }

		-- 1.3.6.1.4.1.43913.16.10.9.1.6.1
		aclConfigEntry OBJECT-TYPE
			SYNTAX AclConfigEntry
			MAX-ACCESS not-accessible
			STATUS current
			DESCRIPTION
				"The entry of acl-Config table."
			INDEX { aclConfigIndex }
			::= { aclConfigTable 1 }

		AclConfigEntry ::=
			SEQUENCE {
				aclConfigIndex
					Integer32,
				aclConfigNo
					Integer32,
				aclRule
					AclRuleType,
				aclProt
					DisplayString,
				aclConfigSource
					DisplayString,
				aclConfigDest
					DisplayString,
				aclConfigOpt
					DisplayString
			 }

		-- 1.3.6.1.4.1.43913.16.10.9.1.6.1.1
		aclConfigIndex OBJECT-TYPE
			SYNTAX Integer32 (1..20)
			MAX-ACCESS not-accessible
			STATUS current
			DESCRIPTION
				"The index of acl-info table."
			::= { aclConfigEntry 1 }


		--  1.3.6.1.4.1.43913.16.10.9.1.6.1.2
		aclConfigNo OBJECT-TYPE
			SYNTAX Integer32
			MAX-ACCESS read-only
			STATUS current
			DESCRIPTION
				"The acl-number of acl-config table."
			::= { aclConfigEntry 2 }


		--  1.3.6.1.4.1.43913.16.10.9.1.6.1.3
		aclRule OBJECT-TYPE
			SYNTAX AclRuleType
			MAX-ACCESS read-only
			STATUS current
			DESCRIPTION
				"acl rule. The value should be deny and permit."
			::= { aclConfigEntry 3 }

		-- 1.3.6.1.4.1.43913.16.10.9.1.6.1.4
		aclProt OBJECT-TYPE
			SYNTAX DisplayString
			MAX-ACCESS read-only
			STATUS current
			DESCRIPTION
				"acl protocol. The value should be tcp udp and all."
			::= { aclConfigEntry 4 }

		-- 1.3.6.1.4.1.43913.16.10.9.1.6.1.5
		aclConfigSource OBJECT-TYPE
			SYNTAX DisplayString
			MAX-ACCESS read-only
			STATUS current
			DESCRIPTION
				"Source address info. Include ipv4/ipv6."
			::= { aclConfigEntry 5 }

		-- 1.3.6.1.4.1.43913.16.10.9.1.6.1.6
		aclConfigDest OBJECT-TYPE
			SYNTAX DisplayString
			MAX-ACCESS read-only
			STATUS current
			DESCRIPTION
				"Destination address info. Include ipv4/ipv6."
			::= { aclConfigEntry 6 }

		-- 1.3.6.1.4.1.43913.16.10.9.1.6.1.7
		aclConfigOpt OBJECT-TYPE
			SYNTAX DisplayString
			MAX-ACCESS read-only
			STATUS current
			DESCRIPTION
				"Option info .Include the port of protocol, tos, dscp, mac."
			::= { aclConfigEntry 7 }

		-- 1.3.6.1.4.1.43913.16.10.9.1.7
		aclSettingTable OBJECT-TYPE
			SYNTAX SEQUENCE OF AclSettingEntry
			MAX-ACCESS not-accessible
			STATUS current
			DESCRIPTION
				"This table is used to add or delete a access-list rule."
			::= { accessList 7 }

		-- 1.3.6.1.4.1.43913.16.10.9.1.7.1
		aclSettingEntry OBJECT-TYPE
			SYNTAX AclSettingEntry
			MAX-ACCESS not-accessible
			STATUS current
			DESCRIPTION
				"The entry of acl-Setting table."
			INDEX { aclSettingIndex }
			::= { aclSettingTable 1 }

		AclSettingEntry ::=
			SEQUENCE {
				aclSettingIndex
					Integer32,
				aclSettingNo
					Integer32,
				aclSettingRule
					AclRuleType,
				aclSettingEtherType
					AclEtherType,
				aclSetting
					DisplayString,
				aclSettingCommit
					AclSetType
			 }

		-- 1.3.6.1.4.1.43913.16.10.9.1.7.1.1
		aclSettingIndex OBJECT-TYPE
			SYNTAX Integer32 (1..1)
			MAX-ACCESS not-accessible
			STATUS current
			DESCRIPTION
				"The index of acl-setting table."
			::= { aclSettingEntry 1 }

		-- 1.3.6.1.4.1.43913.16.10.9.1.7.1.2
		aclSettingNo OBJECT-TYPE
			SYNTAX Integer32 (1..100)
			MAX-ACCESS read-write
			STATUS current
			DESCRIPTION
				"Acl Number."
			::= { aclSettingEntry 2 }

		-- 1.3.6.1.4.1.43913.16.10.9.1.7.1.3
		aclSettingRule OBJECT-TYPE
			SYNTAX AclRuleType
			MAX-ACCESS read-write
			STATUS current
			DESCRIPTION
				"Acl rule. The value should be deny(0) and permit(1)."
			::= { aclSettingEntry 3 }

		-- 1.3.6.1.4.1.43913.16.10.9.1.7.1.4
		aclSettingEtherType OBJECT-TYPE
			SYNTAX AclEtherType
			MAX-ACCESS read-write
			STATUS current
			DESCRIPTION
				"Acl ethertype. The value should be arp(0), ipv4(1), ipv6(2)."
			::= { aclSettingEntry 4 }

		-- 1.3.6.1.4.1.43913.16.10.9.1.7.1.5
		aclSetting OBJECT-TYPE
			SYNTAX DisplayString
			MAX-ACCESS read-write
			STATUS current
			DESCRIPTION
				"The aclSetting. The format is divided into two cases:
				case ipv4: { mac-dest <mac> } | { mac-src <max> } | {icmp} |
					{src {any | <src-addr> netmask <src-netmask>} dest {any | <dest-addr> netmask <dest-netmask>} protocol {tcp|udp}
					source-port {any |<src-port number> <end port>} dest-port {any |<dest-port number> <end port>}
					{tos <tos vaule>|dscp <dscp vaule>}}}
				case ipv6: { mac-dest <mac> } | { mac-src <max> } |
					{src6 {any |<src-ipv6-addr> prefix-length <src-prefix length value>} dest6 {any |<dest-ipv6-addr> prefix-length <dest-
					prefix length value>} protocol {tcp|udp} source-port {any |<src-port number> <end port>} dest-port
					{any |<dest-port number> <end port>} dscp <dscp vaule>}}."
			::= { aclSettingEntry 5 }

		-- 1.3.6.1.4.1.43913.16.10.9.1.7.1.6
		aclSettingCommit OBJECT-TYPE
			SYNTAX AclSetType
			MAX-ACCESS read-write
			STATUS current
			DESCRIPTION
				"commit the acl-setting action. The action should be add(1) and delete(2)"
			::= { aclSettingEntry 6 }

		-- 1.3.6.1.4.1.43913.16.10.9.1.8
		aclCommit OBJECT-TYPE
			SYNTAX AclCommit
			MAX-ACCESS read-write
			STATUS current
			DESCRIPTION
				"commit the acl config."
			::= { accessList 8 }

		-- 1.3.6.1.4.1.43913.16.11
		alarm OBJECT IDENTIFIER ::= { sm2000-5g 11 }


		-- 1.3.6.1.4.1.43913.16.11.1
		alarmConfigTable OBJECT-TYPE
			SYNTAX SEQUENCE OF AlarmConfigEntry
			MAX-ACCESS not-accessible
			STATUS current
			DESCRIPTION
				"Alarm config table."
			::= { alarm 1 }


		-- 1.3.6.1.4.1.43913.16.11.1.1
		alarmConfigEntry OBJECT-TYPE
			SYNTAX AlarmConfigEntry
			MAX-ACCESS not-accessible
			STATUS current
			DESCRIPTION
				"The entry of alarm config table."
			INDEX { alarmConfigIndex }
			::= { alarmConfigTable 1 }


		AlarmConfigEntry ::=
			SEQUENCE {
				alarmConfigIndex
					Integer32,
				alarmID
					Integer32,
				alarmLevel
					AlarmLevel,
				alarmDelay
					Integer32,
				alarmState
					ActionState,
				alarmDescription
					DisplayString,
				actAlarmAllState
					ActionState
			 }

		-- 1.3.6.1.4.1.43913.16.11.1.1.1
		alarmConfigIndex OBJECT-TYPE
			SYNTAX Integer32 (1..108)
			MAX-ACCESS not-accessible
			STATUS current
			DESCRIPTION
				"The index of alarm config table."
			::= { alarmConfigEntry 1 }


		-- 1.3.6.1.4.1.43913.16.11.1.1.2
		alarmID OBJECT-TYPE
			SYNTAX Integer32
			MAX-ACCESS read-only
			STATUS current
			DESCRIPTION
				"Alarm ID."
			::= { alarmConfigEntry 2 }


		-- 1.3.6.1.4.1.43913.16.11.1.1.3
		alarmLevel OBJECT-TYPE
			SYNTAX AlarmLevel
			MAX-ACCESS read-write
			STATUS current
			DESCRIPTION
				"Alarm level. The value should be critical(2), major(3), minor(4), event(5)."
			::= { alarmConfigEntry 3 }


		-- 1.3.6.1.4.1.43913.16.11.1.1.4
		alarmDelay OBJECT-TYPE
			SYNTAX Integer32
			MAX-ACCESS read-write
			STATUS current
			DESCRIPTION
				"Alarm delay."
			::= { alarmConfigEntry 4 }


		-- 1.3.6.1.4.1.43913.16.11.1.1.5
		alarmState OBJECT-TYPE
			SYNTAX ActionState
			MAX-ACCESS read-write
			STATUS current
			DESCRIPTION
				"Alarm state. The value should be enable(1), disable(0)."
			::= { alarmConfigEntry 5 }


		-- 1.3.6.1.4.1.43913.16.11.1.1.6
		alarmDescription OBJECT-TYPE
			SYNTAX DisplayString
			MAX-ACCESS read-only
			STATUS current
			DESCRIPTION
				"Alarm description."
			::= { alarmConfigEntry 6 }


		-- 1.3.6.1.4.1.43913.16.11.1.1.7
		actAlarmAllState OBJECT-TYPE
			SYNTAX ActionState
			MAX-ACCESS write-only
			STATUS current
			DESCRIPTION
				"Set all the alarm state. enable(1), disable(0)"
			::= { alarmConfigEntry 7 }



		-- 1.3.6.1.4.1.43913.16.11.2
		notifyElements OBJECT IDENTIFIER ::= { alarm 2 }


		-- 1.3.6.1.4.1.43913.16.11.2.1
		notifyAID OBJECT-TYPE
			SYNTAX Integer32
			MAX-ACCESS read-only
			STATUS current
			DESCRIPTION
				"Notification alarm ID."
			::= { notifyElements 1 }


		-- 1.3.6.1.4.1.43913.16.11.2.2
		notifyASID OBJECT-TYPE
			SYNTAX Integer32
			MAX-ACCESS read-only
			STATUS current
			DESCRIPTION
				"Notification alarm sub ID."
			::= { notifyElements 2 }


		-- 1.3.6.1.4.1.43913.16.11.2.3
		notifyMod OBJECT-TYPE
			SYNTAX DisplayString
			MAX-ACCESS read-only
			STATUS current
			DESCRIPTION
				"Notification module ID."
			::= { notifyElements 3 }


		-- 1.3.6.1.4.1.43913.16.11.2.4
		notifySeverity OBJECT-TYPE
			SYNTAX AlarmLevel
			MAX-ACCESS read-only
			STATUS current
			DESCRIPTION
				"Notification severity, critical(2), major(3), minor(4), event(5)."
			::= { notifyElements 4 }


		-- 1.3.6.1.4.1.43913.16.11.2.5
		notifyTime OBJECT-TYPE
			SYNTAX DisplayString
			MAX-ACCESS read-only
			STATUS current
			DESCRIPTION
				"The date and time of a notification."
			::= { notifyElements 5 }


		-- 1.3.6.1.4.1.43913.16.11.2.6
		notifyDesc OBJECT-TYPE
			SYNTAX DisplayString
			MAX-ACCESS read-only
			STATUS current
			DESCRIPTION
				"The alarm or event description."
			::= { notifyElements 6 }


		-- 1.3.6.1.4.1.43913.16.11.2.7
		notifyStatus OBJECT-TYPE
			SYNTAX AlarmStatus
			MAX-ACCESS read-only
			STATUS current
			DESCRIPTION
				"The alarm or event status, cleared(0), active(1)."
			::= { notifyElements 7 }


		-- 1.3.6.1.4.1.43913.16.11.3
		sm2000TrapAlarm NOTIFICATION-TYPE
			OBJECTS { notifyAID, notifyMod, notifyStatus, notifyDesc, notifyASID,
				notifyTime, notifySeverity }
			STATUS current
			DESCRIPTION
				"SM2000-5G alarm trap object which specifies alarm module ID, alarm ID, alarm sub ID, alarm status, date and time, severity and description."
			::= { alarm 3 }


		-- 1.3.6.1.4.1.43913.16.11.4
		activeAlarmTable OBJECT-TYPE
			SYNTAX SEQUENCE OF ActiveAlarmEntry
			MAX-ACCESS not-accessible
			STATUS current
			DESCRIPTION
				"The list of current active alarms of the SM2000-5G device."
			::= { alarm 4 }


		-- 1.3.6.1.4.1.43913.16.11.4.1
		activeAlarmEntry OBJECT-TYPE
			SYNTAX ActiveAlarmEntry
			MAX-ACCESS not-accessible
			STATUS current
			DESCRIPTION
				"An alarm entry containing objects of the specified alarm value."
			INDEX { activeAlarmIndex }
			::= { activeAlarmTable 1 }


		ActiveAlarmEntry ::=
			SEQUENCE {
				activeAlarmIndex
					Integer32,
				activeAlarmID
					Integer32,
				activeAlarmSubID
					Integer32,
				activeAlarmModule
					DisplayString,
				activeAlarmLevel
					DisplayString,
				activeAlarmTime
					DisplayString,
				activeAlarmDesc
					DisplayString
			 }

		-- 1.3.6.1.4.1.43913.16.11.4.1.1
		activeAlarmIndex OBJECT-TYPE
			SYNTAX Integer32 (1..100)
			MAX-ACCESS not-accessible
			STATUS current
			DESCRIPTION
				"The access index of the active alarm table.  The range should be 1~100."
			::= { activeAlarmEntry 1 }


		-- 1.3.6.1.4.1.43913.16.11.4.1.2
		activeAlarmID OBJECT-TYPE
			SYNTAX Integer32
			MAX-ACCESS read-only
			STATUS current
			DESCRIPTION
				"This value is the alarm ID."
			::= { activeAlarmEntry 2 }


		-- 1.3.6.1.4.1.43913.16.11.4.1.3
		activeAlarmSubID OBJECT-TYPE
			SYNTAX Integer32
			MAX-ACCESS read-only
			STATUS current
			DESCRIPTION
				"This value is the alarm sub ID."
			::= { activeAlarmEntry 3 }


		-- 1.3.6.1.4.1.43913.16.11.4.1.4
		activeAlarmModule OBJECT-TYPE
			SYNTAX DisplayString
			MAX-ACCESS read-only
			STATUS current
			DESCRIPTION
				"The module ID should be one of MC, CC1, CC2, INPUT1 or INPUT2."
			::= { activeAlarmEntry 4 }


		-- 1.3.6.1.4.1.43913.16.11.4.1.5
		activeAlarmLevel OBJECT-TYPE
			SYNTAX DisplayString
			MAX-ACCESS read-only
			STATUS current
			DESCRIPTION
				"The alarm severity level of the current alarm."
			::= { activeAlarmEntry 5 }


		-- 1.3.6.1.4.1.43913.16.11.4.1.6
		activeAlarmTime OBJECT-TYPE
			SYNTAX DisplayString
			MAX-ACCESS read-only
			STATUS current
			DESCRIPTION
				"The alarm's date and time stamp."
			::= { activeAlarmEntry 6 }


		-- 1.3.6.1.4.1.43913.16.11.4.1.7
		activeAlarmDesc OBJECT-TYPE
			SYNTAX DisplayString
			MAX-ACCESS read-only
			STATUS current
			DESCRIPTION
				"The descriptions of the current active alarm."
			::= { activeAlarmEntry 7 }


		-- 1.3.6.1.4.1.43913.16.11.5
		activeEventTable OBJECT-TYPE
			SYNTAX SEQUENCE OF ActiveEventEntry
			MAX-ACCESS not-accessible
			STATUS current
			DESCRIPTION
				"The list of current active events of the SM2000-5G device."
			::= { alarm 5 }


		-- 1.3.6.1.4.1.43913.16.11.5.1
		activeEventEntry OBJECT-TYPE
			SYNTAX ActiveEventEntry
			MAX-ACCESS not-accessible
			STATUS current
			DESCRIPTION
				"An event entry containing objects of the specified event value."
			INDEX { activeEventIndex }
			::= { activeEventTable 1 }


		ActiveEventEntry ::=
			SEQUENCE {
				activeEventIndex
					Integer32,
				activeEventID
					Integer32,
				activeEventSubID
					Integer32,
				activeEventModule
					DisplayString,
				activeEventLevel
					DisplayString,
				activeEventTime
					DisplayString,
				activeEventDesc
					DisplayString
			 }

		-- 1.3.6.1.4.1.43913.16.11.5.1.1
		activeEventIndex OBJECT-TYPE
			SYNTAX Integer32 (1..100)
			MAX-ACCESS not-accessible
			STATUS current
			DESCRIPTION
				"The access index of the active event table.  The range should be 1~100."
			::= { activeEventEntry 1 }


		-- 1.3.6.1.4.1.43913.16.11.5.1.2
		activeEventID OBJECT-TYPE
			SYNTAX Integer32
			MAX-ACCESS read-only
			STATUS current
			DESCRIPTION
				"This value is the event ID."
			::= { activeEventEntry 2 }


		-- 1.3.6.1.4.1.43913.16.11.5.1.3
		activeEventSubID OBJECT-TYPE
			SYNTAX Integer32
			MAX-ACCESS read-only
			STATUS current
			DESCRIPTION
				"This value is the event sub ID."
			::= { activeEventEntry 3 }


		-- 1.3.6.1.4.1.43913.16.11.5.1.4
		activeEventModule OBJECT-TYPE
			SYNTAX DisplayString
			MAX-ACCESS read-only
			STATUS current
			DESCRIPTION
				"The module ID should be one of MC, CC1, CC2, INPUT1 or INPUT2."
			::= { activeEventEntry 4 }


		-- 1.3.6.1.4.1.43913.16.11.5.1.5
		activeEventLevel OBJECT-TYPE
			SYNTAX DisplayString
			MAX-ACCESS read-only
			STATUS current
			DESCRIPTION
				"It always be EVENT."
			::= { activeEventEntry 5 }


		-- 1.3.6.1.4.1.43913.16.11.5.1.6
		activeEventTime OBJECT-TYPE
			SYNTAX DisplayString
			MAX-ACCESS read-only
			STATUS current
			DESCRIPTION
				"The active event's date and time stamp."
			::= { activeEventEntry 6 }


		-- 1.3.6.1.4.1.43913.16.11.5.1.7
		activeEventDesc OBJECT-TYPE
			SYNTAX DisplayString
			MAX-ACCESS read-only
			STATUS current
			DESCRIPTION
				"The description of the current active event."
			::= { activeEventEntry 7 }



		alarmThresholdConfig OBJECT IDENTIFIER ::= { alarm 6 }


		-- 1.3.6.1.4.1.43913.16.11.6.1
		thresholdMTIElimit1Table OBJECT-TYPE
			SYNTAX SEQUENCE OF ThresholdMTIElimit1Entry
			MAX-ACCESS not-accessible
			STATUS current
			DESCRIPTION
				"The list of MTIE limit1 threshold configuration of the SM2000-5G device."
			::= { alarmThresholdConfig 1 }


		-- 1.3.6.1.4.1.43913.16.11.6.1.1
		thresholdMTIElimit1Entry OBJECT-TYPE
			SYNTAX ThresholdMTIElimit1Entry
			MAX-ACCESS not-accessible
			STATUS current
			DESCRIPTION
				"An MTIE limit1 threshold config entry containing objects of the specified MTIE limit1 threshold value."
			INDEX { thresholdMTIElimit1SlotIndex, thresholdMTIElimit1InputIndex, thresholdMTIElimit1TAUindex }
			::= { thresholdMTIElimit1Table 1 }


		ThresholdMTIElimit1Entry ::=
			SEQUENCE {
				thresholdMTIElimit1SlotIndex
					Integer32,
				thresholdMTIElimit1InputIndex
					Integer32,
				thresholdMTIElimit1TAUindex
					Integer32,
				thresholdMTIElimit1Value
					Integer32
			 }

		-- 1.3.6.1.4.1.43913.16.11.6.1.1.1
		thresholdMTIElimit1SlotIndex OBJECT-TYPE
			SYNTAX Integer32 (1..2)
			MAX-ACCESS read-only
			STATUS current
			DESCRIPTION
				"The input card slot index: 1~2"
			::= { thresholdMTIElimit1Entry 1 }


		-- 1.3.6.1.4.1.43913.16.11.6.1.1.2
		thresholdMTIElimit1InputIndex OBJECT-TYPE
			SYNTAX Integer32 (1..2)
			MAX-ACCESS read-only
			STATUS current
			DESCRIPTION
				"The input signal type index: e1(1), pps(2)"
			::= { thresholdMTIElimit1Entry 2 }


		-- 1.3.6.1.4.1.43913.16.11.6.1.1.3
		thresholdMTIElimit1TAUindex OBJECT-TYPE
			SYNTAX Integer32 (1..13)
			MAX-ACCESS read-only
			STATUS current
			DESCRIPTION
				"The TAU index: 1s(1), 4s(2), 10s(3), 40s(4), 100s(5), 300s(6)
								900s(7), 1800s(8), 3600s(9), 7200s(10), 14400(11)
								28800(12), 86400s(13)"
			::= { thresholdMTIElimit1Entry 3 }


		-- 1.3.6.1.4.1.43913.16.11.6.2.1.4
		thresholdMTIElimit1Value OBJECT-TYPE
			SYNTAX Integer32
			MAX-ACCESS read-write
			STATUS current
			DESCRIPTION
				"The threshold value,default value:
				{0,0,80,0,800,0,1600,0,0,2104,0,0,4055}"
			::= { thresholdMTIElimit1Entry 4 }



		-- 1.3.6.1.4.1.43913.16.11.6.2
		thresholdMTIElimit2Table OBJECT-TYPE
			SYNTAX SEQUENCE OF ThresholdMTIElimit2Entry
			MAX-ACCESS not-accessible
			STATUS current
			DESCRIPTION
				"The list of MTIE limit2 threshold configuration of the SM2000-5G device."
			::= { alarmThresholdConfig 2 }


		-- 1.3.6.1.4.1.43913.16.11.6.2.1
		thresholdMTIElimit2Entry OBJECT-TYPE
			SYNTAX ThresholdMTIElimit2Entry
			MAX-ACCESS not-accessible
			STATUS current
			DESCRIPTION
				"An MTIE limit2 threshold config entry containing objects of the specified MTIE limit2 threshold value."
			INDEX { thresholdMTIElimit2SlotIndex, thresholdMTIElimit2InputIndex, thresholdMTIElimit2TAUindex }
			::= { thresholdMTIElimit2Table 1 }


		ThresholdMTIElimit2Entry ::=
			SEQUENCE {
				thresholdMTIElimit2SlotIndex
					Integer32,
				thresholdMTIElimit2InputIndex
					Integer32,
				thresholdMTIElimit2TAUindex
					Integer32,
				thresholdMTIElimit2Value
					Integer32
			 }

		-- 1.3.6.1.4.1.43913.16.11.6.2.1.1
		thresholdMTIElimit2SlotIndex OBJECT-TYPE
			SYNTAX Integer32 (1..2)
			MAX-ACCESS read-only
			STATUS current
			DESCRIPTION
				"The input card slot index: 1~2"
			::= { thresholdMTIElimit2Entry 1 }


		-- 1.3.6.1.4.1.43913.16.11.6.2.1.2
		thresholdMTIElimit2InputIndex OBJECT-TYPE
			SYNTAX Integer32 (1..2)
			MAX-ACCESS read-only
			STATUS current
			DESCRIPTION
				"The input signal type index: e1(1), pps(2)"
			::= { thresholdMTIElimit2Entry 2 }


		-- 1.3.6.1.4.1.43913.16.11.6.2.1.3
		thresholdMTIElimit2TAUindex OBJECT-TYPE
			SYNTAX Integer32 (1..13)
			MAX-ACCESS read-only
			STATUS current
			DESCRIPTION
				"The TAU index: 1s(1), 4s(2), 10s(3), 40s(4), 100s(5), 300s(6)
								900s(7), 1800s(8), 3600s(9), 7200s(10), 14400(11)
								28800(12), 86400s(13)"
			::= { thresholdMTIElimit2Entry 3 }


		-- 1.3.6.1.4.1.43913.16.11.6.2.1.4
		thresholdMTIElimit2Value OBJECT-TYPE
			SYNTAX Integer32
			MAX-ACCESS read-write
			STATUS current
			DESCRIPTION
				"The threshold value,default value:
				{0,0,100,0,1000,0,2000,0,0,2630,0,0,5069}"
			::= { thresholdMTIElimit2Entry 4 }

		-- 1.3.6.1.4.1.43913.16.11.6.3
		thresholdTDEVTable OBJECT-TYPE
			SYNTAX SEQUENCE OF ThresholdTDEVEntry
			MAX-ACCESS not-accessible
			STATUS current
			DESCRIPTION
				"The list of TDEV threshold configuration of the SM2000-5G device."
			::= { alarmThresholdConfig 3 }


		-- 1.3.6.1.4.1.43913.16.11.6.3.1
		thresholdTDEVEntry OBJECT-TYPE
			SYNTAX ThresholdTDEVEntry
			MAX-ACCESS not-accessible
			STATUS current
			DESCRIPTION
				"An TDEV threshold config entry containing objects of the specified TDEV threshold value."
			INDEX { thresholdTDEVSlotIndex, thresholdTDEVInputIndex, thresholdTDEVTAUindex }
			::= { thresholdTDEVTable 1 }


		ThresholdTDEVEntry ::=
			SEQUENCE {
				thresholdTDEVSlotIndex
					Integer32,
				thresholdTDEVInputIndex
					Integer32,
				thresholdTDEVTAUindex
					Integer32,
				thresholdTDEVValue
					DisplayString
			 }

		-- 1.3.6.1.4.1.43913.16.11.6.3.1.1
		thresholdTDEVSlotIndex OBJECT-TYPE
			SYNTAX Integer32 (1..2)
			MAX-ACCESS read-only
			STATUS current
			DESCRIPTION
				"The input card slot index: 1~2"
			::= { thresholdTDEVEntry 1 }


		-- 1.3.6.1.4.1.43913.16.11.6.3.1.2
		thresholdTDEVInputIndex OBJECT-TYPE
			SYNTAX Integer32 (1..2)
			MAX-ACCESS read-only
			STATUS current
			DESCRIPTION
				"The input signal type index: e1(1), pps(2)"
			::= { thresholdTDEVEntry 2 }


		-- 1.3.6.1.4.1.43913.16.11.6.3.1.3
		thresholdTDEVTAUindex OBJECT-TYPE
			SYNTAX Integer32 (1..13)
			MAX-ACCESS read-only
			STATUS current
			DESCRIPTION
				"The TAU index: 1s(1), 2s(2), 4s(3), 8s(4), 16s(5), 32s(6)
								64s(7), 128s(8), 256s(9), 512s(10), 1024(11)"
			::= { thresholdTDEVEntry 3 }

		-- 1.3.6.1.4.1.43913.16.11.6.3.1.4
		thresholdTDEVValue OBJECT-TYPE
			SYNTAX DisplayString
			MAX-ACCESS read-write
			STATUS current
			DESCRIPTION
				"The threshold value. Accuate to two digits after the decimal point: 0.01.
				Default value:
				{0.00,0.00,0.00,3.00,0.00,0.00,3.00,0.00,7.68,0.00,30.00}"
			::= { thresholdTDEVEntry 4 }



		-- 1.3.6.1.4.1.43913.16.11.6.4
		thresholdFREQTable OBJECT-TYPE
			SYNTAX SEQUENCE OF ThresholdFREQEntry
			MAX-ACCESS not-accessible
			STATUS current
			DESCRIPTION
				"The list of FREQ threshold configuration of the SM2000-5G device."
			::= { alarmThresholdConfig 4 }


		-- 1.3.6.1.4.1.43913.16.11.6.4.1
		thresholdFREQEntry OBJECT-TYPE
			SYNTAX ThresholdFREQEntry
			MAX-ACCESS not-accessible
			STATUS current
			DESCRIPTION
				"An FREQ threshold config entry containing objects of the specified FREQ threshold value."
			INDEX { thresholdFREQSlotIndex, thresholdFREQInputIndex, thresholdFREQTAUindex }
			::= { thresholdFREQTable 1 }


		ThresholdFREQEntry ::=
			SEQUENCE {
				thresholdFREQSlotIndex
					Integer32,
				thresholdFREQInputIndex
					Integer32,
				thresholdFREQTAUindex
					Integer32,
				thresholdFREQValue
					DisplayString
			 }

		-- 1.3.6.1.4.1.43913.16.11.6.4.1.1
		thresholdFREQSlotIndex OBJECT-TYPE
			SYNTAX Integer32 (1..2)
			MAX-ACCESS read-only
			STATUS current
			DESCRIPTION
				"The input card slot index: 1~2"
			::= { thresholdFREQEntry 1 }


		-- 1.3.6.1.4.1.43913.16.11.6.4.1.2
		thresholdFREQInputIndex OBJECT-TYPE
			SYNTAX Integer32 (1..2)
			MAX-ACCESS read-only
			STATUS current
			DESCRIPTION
				"The input signal type index: e1(1), pps(2)"
			::= { thresholdFREQEntry 2 }


		-- 1.3.6.1.4.1.43913.16.11.6.4.1.3
		thresholdFREQTAUindex OBJECT-TYPE
			SYNTAX Integer32 (1..13)
			MAX-ACCESS read-only
			STATUS current
			DESCRIPTION
				"The TAU index: 1s(1), 2s(2), 4s(3), 8s(4), 16s(5), 32s(6)
								64s(7), 128s(8), 256s(9), 512s(10), 1024(11)"
			::= { thresholdFREQEntry 3 }

		-- 1.3.6.1.4.1.43913.16.11.6.4.1.4
		thresholdFREQValue OBJECT-TYPE
			SYNTAX DisplayString
			MAX-ACCESS read-write
			STATUS current
			DESCRIPTION
				"The threshold value. Accuate to two digits after the decimal point: 0.01
				Default value:
				{0.00,0.00,0.00,10.00,0.00,0.00,60.00,0.00,300.00,0.00,1500.00}"
			::= { thresholdFREQEntry 4 }




		-- 1.3.6.1.4.1.43913.16.12
		log OBJECT IDENTIFIER ::= { sm2000-5g 12 }


		-- 1.3.6.1.4.1.43913.16.12.1
		alarmLogTable OBJECT-TYPE
			SYNTAX SEQUENCE OF AlarmLogEntry
			MAX-ACCESS not-accessible
			STATUS current
			DESCRIPTION
				"The table is used to get alarm log for SM2000-5G."
			::= { log 1 }


		-- 1.3.6.1.4.1.43913.16.12.1.1
		alarmLogEntry OBJECT-TYPE
			SYNTAX AlarmLogEntry
			MAX-ACCESS not-accessible
			STATUS current
			DESCRIPTION
				"The entry of alarm log table."
			INDEX { alarmLogIndex }
			::= { alarmLogTable 1 }


		AlarmLogEntry ::=
			SEQUENCE {
				alarmLogIndex
					Integer32,
				alarmLogDesc
					DisplayString
			 }

		-- 1.3.6.1.4.1.43913.16.12.1.1.1
		alarmLogIndex OBJECT-TYPE
			SYNTAX Integer32 (1..500)
			MAX-ACCESS not-accessible
			STATUS current
			DESCRIPTION
				"The index of alarm log table."
			::= { alarmLogEntry 1 }


		-- 1.3.6.1.4.1.43913.16.12.1.1.2
		alarmLogDesc OBJECT-TYPE
			SYNTAX DisplayString
			MAX-ACCESS read-only
			STATUS current
			DESCRIPTION
				"The alarm description."
			::= { alarmLogEntry 2 }


		-- 1.3.6.1.4.1.43913.16.12.2
		eventLogTable OBJECT-TYPE
			SYNTAX SEQUENCE OF EventLogEntry
			MAX-ACCESS not-accessible
			STATUS current
			DESCRIPTION
				"The table is used to get event log for SM2000-5G."
			::= { log 2 }


		-- 1.3.6.1.4.1.43913.16.12.2.1
		eventLogEntry OBJECT-TYPE
			SYNTAX EventLogEntry
			MAX-ACCESS not-accessible
			STATUS current
			DESCRIPTION
				"The entry of event log table."
			INDEX { eventLogIndex }
			::= { eventLogTable 1 }


		EventLogEntry ::=
			SEQUENCE {
				eventLogIndex
					Integer32,
				eventLogDesc
					DisplayString
			 }

		-- 1.3.6.1.4.1.43913.16.12.2.1.1
		eventLogIndex OBJECT-TYPE
			SYNTAX Integer32 (1..500)
			MAX-ACCESS not-accessible
			STATUS current
			DESCRIPTION
				"The index of event log table."
			::= { eventLogEntry 1 }


		-- 1.3.6.1.4.1.43913.16.12.2.1.2
		eventLogDesc OBJECT-TYPE
			SYNTAX DisplayString
			MAX-ACCESS read-only
			STATUS current
			DESCRIPTION
				"The event description."
			::= { eventLogEntry 2 }


		-- 1.3.6.1.4.1.43913.16.12.3
		cmdLogTable OBJECT-TYPE
			SYNTAX SEQUENCE OF CmdLogEntry
			MAX-ACCESS not-accessible
			STATUS current
			DESCRIPTION
				"The table is used to get command log for SM2000-5G."
			::= { log 3 }


		-- 1.3.6.1.4.1.43913.16.12.3.1
		cmdLogEntry OBJECT-TYPE
			SYNTAX CmdLogEntry
			MAX-ACCESS not-accessible
			STATUS current
			DESCRIPTION
				"The entry of command log table."
			INDEX { cmdLogIndex }
			::= { cmdLogTable 1 }


		CmdLogEntry ::=
			SEQUENCE {
				cmdLogIndex
					Integer32,
				cmdLogDesc
					DisplayString
			 }

		-- 1.3.6.1.4.1.43913.16.12.3.1.1
		cmdLogIndex OBJECT-TYPE
			SYNTAX Integer32 (1..500)
			MAX-ACCESS not-accessible
			STATUS current
			DESCRIPTION
				"The index of command log table."
			::= { cmdLogEntry 1 }


		-- 1.3.6.1.4.1.43913.16.12.3.1.2
		cmdLogDesc OBJECT-TYPE
			SYNTAX DisplayString
			MAX-ACCESS read-only
			STATUS current
			DESCRIPTION
				"The description of the command details."
			::= { cmdLogEntry 2 }


		-- 1.3.6.1.4.1.43913.16.12.4
		secuLogTable OBJECT-TYPE
			SYNTAX SEQUENCE OF SecuLogEntry
			MAX-ACCESS not-accessible
			STATUS current
			DESCRIPTION
				"The table is used to get security log for SM2000-5G."
			::= { log 4 }


		-- 1.3.6.1.4.1.43913.16.12.4.1
		secuLogEntry OBJECT-TYPE
			SYNTAX SecuLogEntry
			MAX-ACCESS not-accessible
			STATUS current
			DESCRIPTION
				"The entry of security log table."
			INDEX { secuLogIndex }
			::= { secuLogTable 1 }


		SecuLogEntry ::=
			SEQUENCE {
				secuLogIndex
					Integer32,
				secuLogDesc
					DisplayString
			 }

		-- 1.3.6.1.4.1.43913.16.12.4.1.1
		secuLogIndex OBJECT-TYPE
			SYNTAX Integer32 (1..500)
			MAX-ACCESS not-accessible
			STATUS current
			DESCRIPTION
				"The index of security log table."
			::= { secuLogEntry 1 }


		-- 1.3.6.1.4.1.43913.16.12.4.1.2
		secuLogDesc OBJECT-TYPE
			SYNTAX DisplayString
			MAX-ACCESS read-only
			STATUS current
			DESCRIPTION
				"The description of the security details."
			::= { secuLogEntry 2 }


		-- 1.3.6.1.4.1.43913.16.13
		performance OBJECT IDENTIFIER ::= { sm2000-5g 13 }


		-- 1.3.6.1.4.1.43913.16.13.1
		performanceDayCfgTable OBJECT-TYPE
			SYNTAX SEQUENCE OF PerformanceDayCfgEntry
			MAX-ACCESS not-accessible
			STATUS current
			DESCRIPTION
				"This table is used to set input E1 performance day."
			::= { performance 1 }


		-- 1.3.6.1.4.1.43913.16.13.1.1
		performanceDayCfgEntry OBJECT-TYPE
			SYNTAX PerformanceDayCfgEntry
			MAX-ACCESS not-accessible
			STATUS current
			DESCRIPTION
				"The entry of the table."
			INDEX { dayCfgIndex }
			::= { performanceDayCfgTable 1 }


		PerformanceDayCfgEntry ::=
			SEQUENCE {
				dayCfgIndex
					Integer32,
				dayCfgPort
					Inputchn,
				dayCfgType
					DisplayString,
				cfgDay
					Integer32
			 }

		-- 1.3.6.1.4.1.43913.16.13.1.1.1
		dayCfgIndex OBJECT-TYPE
			SYNTAX Integer32 (1..80)
			MAX-ACCESS not-accessible
			STATUS current
			DESCRIPTION
				"The index of the table."
			::= { performanceDayCfgEntry 1 }


		-- 1.3.6.1.4.1.43913.16.13.1.1.2
		dayCfgPort OBJECT-TYPE
			SYNTAX Inputchn
			MAX-ACCESS read-only
			STATUS current
			DESCRIPTION
				"The configration port, the value is 1 to 20."
			::= { performanceDayCfgEntry 2 }


		-- 1.3.6.1.4.1.43913.16.13.1.1.3
		dayCfgType OBJECT-TYPE
			SYNTAX DisplayString
			MAX-ACCESS read-only
			STATUS current
			DESCRIPTION
				"The type for the configration, the value is MTIE, TDEV, FREQ, PHASE1M."
			::= { performanceDayCfgEntry 3 }


		-- 1.3.6.1.4.1.43913.16.13.1.1.4
		cfgDay OBJECT-TYPE
			SYNTAX Integer32 (0..7)
			MAX-ACCESS read-write
			STATUS current
			DESCRIPTION
				"The value of day, the range is 0~7."
			::= { performanceDayCfgEntry 4 }


		-- 1.3.6.1.4.1.43913.16.13.2
		mtieTable OBJECT-TYPE
			SYNTAX SEQUENCE OF MtieEntry
			MAX-ACCESS not-accessible
			STATUS current
			DESCRIPTION
				"The mtie performance table."
			::= { performance 2 }


		-- 1.3.6.1.4.1.43913.16.13.2.1
		mtieEntry OBJECT-TYPE
			SYNTAX MtieEntry
			MAX-ACCESS not-accessible
			STATUS current
			DESCRIPTION
				"The entry of mtie performance table."
			INDEX { mtieIndex }
			::= { mtieTable 1 }


		MtieEntry ::=
			SEQUENCE {
				mtieIndex
					Integer32,
				mtiePort
					Inputchn,
				mtieDuration
					Integer32,
				mtieValue
					Unsigned32,
				mtieSamplTime
					DisplayString
			 }

		-- 1.3.6.1.4.1.43913.16.13.2.1.1
		mtieIndex OBJECT-TYPE
			SYNTAX Integer32 (1..260)
			MAX-ACCESS not-accessible
			STATUS current
			DESCRIPTION
				"The index of mtie performance table."
			::= { mtieEntry 1 }


		-- 1.3.6.1.4.1.43913.16.13.2.1.2
		mtiePort OBJECT-TYPE
			SYNTAX Inputchn
			MAX-ACCESS read-only
			STATUS current
			DESCRIPTION
				"The port number of the performance, the value is 1 to 20."
			::= { mtieEntry 2 }


		-- 1.3.6.1.4.1.43913.16.13.2.1.3
		mtieDuration OBJECT-TYPE
			SYNTAX Integer32
			MAX-ACCESS read-only
			STATUS current
			DESCRIPTION
				"The time duration of the performance."
			::= { mtieEntry 3 }


		-- 1.3.6.1.4.1.43913.16.13.2.1.4
		mtieValue OBJECT-TYPE
			SYNTAX Unsigned32
			MAX-ACCESS read-only
			STATUS current
			DESCRIPTION
				"The mtie value in a time duration."
			::= { mtieEntry 4 }


		-- 1.3.6.1.4.1.43913.16.13.2.1.5
		mtieSamplTime OBJECT-TYPE
			SYNTAX DisplayString
			MAX-ACCESS read-only
			STATUS current
			DESCRIPTION
				"The mtie sampling time."
			::= { mtieEntry 5 }



		-- 1.3.6.1.4.1.43913.16.13.3
		tdevTable OBJECT-TYPE
			SYNTAX SEQUENCE OF TdevEntry
			MAX-ACCESS not-accessible
			STATUS current
			DESCRIPTION
				"The tdev performance table."
			::= { performance 3 }


		-- 1.3.6.1.4.1.43913.16.13.3.1
		tdevEntry OBJECT-TYPE
			SYNTAX TdevEntry
			MAX-ACCESS not-accessible
			STATUS current
			DESCRIPTION
				"The entry of tdev performance table."
			INDEX { tdevIndex }
			::= { tdevTable 1 }


		TdevEntry ::=
			SEQUENCE {
				tdevIndex
					Integer32,
				tdevPort
					Inputchn,
				tdevDuration
					Integer32,
				tdevValue
					DisplayString,
				tdevSamplTime
					DisplayString
			 }

		-- 1.3.6.1.4.1.43913.16.13.3.1.1
		tdevIndex OBJECT-TYPE
			SYNTAX Integer32 (1..220)
			MAX-ACCESS not-accessible
			STATUS current
			DESCRIPTION
				"The index of tdev performance table."
			::= { tdevEntry 1 }


		-- 1.3.6.1.4.1.43913.16.13.3.1.2
		tdevPort OBJECT-TYPE
			SYNTAX Inputchn
			MAX-ACCESS read-only
			STATUS current
			DESCRIPTION
				"The port number of the performance, the value is 1 to 20."
			::= { tdevEntry 2 }


		-- 1.3.6.1.4.1.43913.16.13.3.1.3
		tdevDuration OBJECT-TYPE
			SYNTAX Integer32
			MAX-ACCESS read-only
			STATUS current
			DESCRIPTION
				"The time duration of the performance."
			::= { tdevEntry 3 }


		-- 1.3.6.1.4.1.43913.16.13.3.1.4
		tdevValue OBJECT-TYPE
			SYNTAX DisplayString
			MAX-ACCESS read-only
			STATUS current
			DESCRIPTION
				"The tdev value in a time duration."
			::= { tdevEntry 4 }


		-- 1.3.6.1.4.1.43913.16.13.3.1.5
		tdevSamplTime OBJECT-TYPE
			SYNTAX DisplayString
			MAX-ACCESS read-only
			STATUS current
			DESCRIPTION
				"The tdev sampling time."
			::= { tdevEntry 5 }


		-- 1.3.6.1.4.1.43913.16.13.4
		freqTable OBJECT-TYPE
			SYNTAX SEQUENCE OF FreqEntry
			MAX-ACCESS not-accessible
			STATUS current
			DESCRIPTION
				"The freq performance table."
			::= { performance 4 }


		-- 1.3.6.1.4.1.43913.16.13.4.1
		freqEntry OBJECT-TYPE
			SYNTAX FreqEntry
			MAX-ACCESS not-accessible
			STATUS current
			DESCRIPTION
				"The entry of freq performance table."
			INDEX { freqIndex }
			::= { freqTable 1 }


		FreqEntry ::=
			SEQUENCE {
				freqIndex
					Integer32,
				freqPort
					Inputchn,
				freqDuration
					Integer32,
				freqValue
					DisplayString,
				freqSamplTime
					DisplayString
			 }

		-- 1.3.6.1.4.1.43913.16.13.4.1.1
		freqIndex OBJECT-TYPE
			SYNTAX Integer32 (1..220)
			MAX-ACCESS not-accessible
			STATUS current
			DESCRIPTION
				"The index of freq performance table."
			::= { freqEntry 1 }


		-- 1.3.6.1.4.1.43913.16.13.4.1.2
		freqPort OBJECT-TYPE
			SYNTAX Inputchn
			MAX-ACCESS read-only
			STATUS current
			DESCRIPTION
				"The port number of the performance, the value is 1 to 20."
			::= { freqEntry 2 }


		-- 1.3.6.1.4.1.43913.16.13.4.1.3
		freqDuration OBJECT-TYPE
			SYNTAX Integer32
			MAX-ACCESS read-only
			STATUS current
			DESCRIPTION
				"The time duration of the performance."
			::= { freqEntry 3 }


		-- 1.3.6.1.4.1.43913.16.13.4.1.4
		freqValue OBJECT-TYPE
			SYNTAX DisplayString
			MAX-ACCESS read-only
			STATUS current
			DESCRIPTION
				"The freq value in a time duration."
			::= { freqEntry 4 }


		-- 1.3.6.1.4.1.43913.16.13.4.1.5
		freqSamplTime OBJECT-TYPE
			SYNTAX DisplayString
			MAX-ACCESS read-only
			STATUS current
			DESCRIPTION
				"The freq sampling time."
			::= { freqEntry 5 }


		-- 1.3.6.1.4.1.43913.16.13.5
		phaseTable OBJECT-TYPE
			SYNTAX SEQUENCE OF PhaseEntry
			MAX-ACCESS not-accessible
			STATUS current
			DESCRIPTION
				"The phase data table."
			::= { performance 5 }


		-- 1.3.6.1.4.1.43913.16.13.5.1
		phaseEntry OBJECT-TYPE
			SYNTAX PhaseEntry
			MAX-ACCESS not-accessible
			STATUS current
			DESCRIPTION
				"The entry of phase data table."
			INDEX { phaseIndex }
			::= { phaseTable 1 }


		PhaseEntry ::=
			SEQUENCE {
				phaseIndex
					Integer32,
				phasePort
					Inputchn,
				phaseData
					OCTET STRING,
				phaseSamplTime
					DisplayString
			 }

		-- 1.3.6.1.4.1.43913.16.13.5.1.1
		phaseIndex OBJECT-TYPE
			SYNTAX Integer32 (1..216)
			MAX-ACCESS not-accessible
			STATUS current
			DESCRIPTION
				"The index of phase data table."
			::= { phaseEntry 1 }


		-- 1.3.6.1.4.1.43913.16.13.5.1.2
		phasePort OBJECT-TYPE
			SYNTAX Inputchn
			MAX-ACCESS read-only
			STATUS current
			DESCRIPTION
				"The port number of the performance, the value is 1 to 24."
			::= { phaseEntry 2 }


		-- 1.3.6.1.4.1.43913.16.13.5.1.3
		phaseData OBJECT-TYPE
			SYNTAX OCTET STRING (SIZE (0..1023))
			MAX-ACCESS read-only
			STATUS current
			DESCRIPTION
				"The phase data."
			::= { phaseEntry 3 }


		-- 1.3.6.1.4.1.43913.16.13.5.1.4
		phaseSamplTime OBJECT-TYPE
			SYNTAX DisplayString
			MAX-ACCESS read-only
			STATUS current
			DESCRIPTION
				"The phase sampling time."
			::= { phaseEntry 4 }


		-- 1.3.6.1.4.1.43913.16.13.6
		phase1MTable OBJECT-TYPE
			SYNTAX SEQUENCE OF Phase1MEntry
			MAX-ACCESS not-accessible
			STATUS current
			DESCRIPTION
				"The phase-1m data table."
			::= { performance 6 }


		-- 1.3.6.1.4.1.43913.16.13.6.1
		phase1MEntry OBJECT-TYPE
			SYNTAX Phase1MEntry
			MAX-ACCESS not-accessible
			STATUS current
			DESCRIPTION
				"The entry of phase-1m data table."
			INDEX { phase1MIndex }
			::= { phase1MTable 1 }


		Phase1MEntry ::=
			SEQUENCE {
				phase1MIndex
					Integer32,
				phase1MPort
					Inputchn,
				phase1MData
					OCTET STRING,
				phase1MSamplTime
					DisplayString
			 }

		-- 1.3.6.1.4.1.43913.16.13.6.1.1
		phase1MIndex OBJECT-TYPE
			SYNTAX Integer32 (1..20)
			MAX-ACCESS not-accessible
			STATUS current
			DESCRIPTION
				"The entry of phase-1m data table."
			::= { phase1MEntry 1 }


		-- 1.3.6.1.4.1.43913.16.13.6.1.2
		phase1MPort OBJECT-TYPE
			SYNTAX Inputchn
			MAX-ACCESS read-only
			STATUS current
			DESCRIPTION
				"The port number of the performance, the value is 1 to 22."
			::= { phase1MEntry 2 }


		-- 1.3.6.1.4.1.43913.16.13.6.1.3
		phase1MData OBJECT-TYPE
			SYNTAX OCTET STRING (SIZE (0..1023))
			MAX-ACCESS read-only
			STATUS current
			DESCRIPTION
				"The phase-1m data."
			::= { phase1MEntry 3 }


		-- 1.3.6.1.4.1.43913.16.13.6.1.4
		phase1MSamplTime OBJECT-TYPE
			SYNTAX DisplayString
			MAX-ACCESS read-only
			STATUS current
			DESCRIPTION
				"The phase-1m sampling time."
			::= { phase1MEntry 4 }

		-- 1.3.6.1.4.1.43913.16.13.7
		sm2000PhaseElements OBJECT IDENTIFIER ::= { performance 7 }


		-- 1.3.6.1.4.1.43913.16.13.7.1
		notifyPhasePortIndex OBJECT-TYPE
			SYNTAX Integer32 (1..14)
			MAX-ACCESS read-only
			STATUS current
			DESCRIPTION
				"Notification Phase port index."
			::= { sm2000PhaseElements 1 }


		-- 1.3.6.1.4.1.43913.16.13.7.2
		notifyPhasePortDate OBJECT-TYPE
			SYNTAX DisplayString
			MAX-ACCESS read-only
			STATUS current
			DESCRIPTION
				"Notification Phase date (1 minute)."
			::= { sm2000PhaseElements 2 }


		-- 1.3.6.1.4.1.43913.16.13.7.3
		notifyPhaseTimestamp OBJECT-TYPE
			SYNTAX DisplayString
			MAX-ACCESS read-only
			STATUS current
			DESCRIPTION
				"Notification Phase timestamp."
			::= { sm2000PhaseElements 3 }

		-- 1.3.6.1.4.1.43913.16.13.8
		sm2000Phase1M NOTIFICATION-TYPE
		OBJECTS { notifyPhasePortIndex,notifyPhasePortDate,notifyPhaseTimestamp  }
		STATUS current
		DESCRIPTION
			"SM2000-5G Phase trap object which specifies prot-index, phase-value, phase-timestamp"
		::= { performance 8 }




		-- 1.3.6.1.4.1.43913.16.13.9
		sm2000mtieElements OBJECT IDENTIFIER ::= { performance 9 }


		-- 1.3.6.1.4.1.43913.16.13.9.1
		notifyMTIEPortIndex OBJECT-TYPE
			SYNTAX Integer32 (1..14)
			MAX-ACCESS read-only
			STATUS current
			DESCRIPTION
				"Notification MTIE port index."
			::= { sm2000mtieElements 1 }


		-- 1.3.6.1.4.1.43913.16.13.9.2
		notifyMTIEPortDate OBJECT-TYPE
			SYNTAX DisplayString
			MAX-ACCESS read-only
			STATUS current
			DESCRIPTION
				"Notification MTIE date."
			::= { sm2000mtieElements 2 }


		-- 1.3.6.1.4.1.43913.16.13.9.3
		notifyMTIETimestamp OBJECT-TYPE
			SYNTAX DisplayString
			MAX-ACCESS read-only
			STATUS current
			DESCRIPTION
				"Notification MTIE timestamp."
			::= { sm2000mtieElements 3 }

		-- 1.3.6.1.4.1.43913.16.13.9
		sm2000MTIE NOTIFICATION-TYPE
		OBJECTS { notifyMTIEPortIndex,notifyMTIEPortDate,notifyMTIETimestamp  }
		STATUS current
		DESCRIPTION
			"SM2000-5G MTIE trap object which specifies prot-index, value, timestamp"
		::= { performance 10 }



		-- 1.3.6.1.4.1.43913.16.13.11
		sm2000tdevElements OBJECT IDENTIFIER ::= { performance 11 }


		-- 1.3.6.1.4.1.43913.16.13.9.1
		notifyTDEVPortIndex OBJECT-TYPE
			SYNTAX Integer32 (1..14)
			MAX-ACCESS read-only
			STATUS current
			DESCRIPTION
				"Notification TDEV port index."
			::= { sm2000tdevElements 1 }


		-- 1.3.6.1.4.1.43913.16.13.9.2
		notifyTDEVPortDate OBJECT-TYPE
			SYNTAX DisplayString
			MAX-ACCESS read-only
			STATUS current
			DESCRIPTION
				"Notification TDEV date."
			::= { sm2000tdevElements 2 }


		-- 1.3.6.1.4.1.43913.16.13.9.3
		notifyTDEVTimestamp OBJECT-TYPE
			SYNTAX DisplayString
			MAX-ACCESS read-only
			STATUS current
			DESCRIPTION
				"Notification TDEV timestamp."
			::= { sm2000tdevElements 3 }

		-- 1.3.6.1.4.1.43913.16.13.9
		sm2000TDEV NOTIFICATION-TYPE
		OBJECTS { notifyTDEVPortIndex,notifyTDEVPortDate,notifyTDEVTimestamp  }
		STATUS current
		DESCRIPTION
			"SM2000-5G TDEV trap object which specifies prot-index, value, timestamp"
		::= { performance 12 }

		-- 1.3.6.1.4.1.43913.16.13.13
		restartPM OBJECT-TYPE
			SYNTAX Inputchn
			MAX-ACCESS read-write
			STATUS current
			DESCRIPTION
				"Restart input performance monitoring.
				This item is write-only.
				The read of item is invalid."
			::= { performance 13 }

		-- 1.3.6.1.4.1.43913.16.13.14
		setSlot1PMRef OBJECT-TYPE
			SYNTAX PPSchn
			MAX-ACCESS read-write
			STATUS current
			DESCRIPTION
				"Set PM reference for slot1"
			::= { performance 14 }

		-- 1.3.6.1.4.1.43913.16.13.15
		setSlot1PMSrc OBJECT-TYPE
			SYNTAX PPSchn
			MAX-ACCESS read-write
			STATUS current
			DESCRIPTION
				"Set PM source for slot1"
			::= { performance 15 }

		-- 1.3.6.1.4.1.43913.16.13.16
		setSlot2PMRef OBJECT-TYPE
			SYNTAX PPSchn
			MAX-ACCESS read-write
			STATUS current
			DESCRIPTION
				"Set PM reference for slot2"
			::= { performance 16 }

		-- 1.3.6.1.4.1.43913.16.13.17
		setSlot2PMSrc OBJECT-TYPE
			SYNTAX PPSchn
			MAX-ACCESS read-write
			STATUS current
			DESCRIPTION
				"Set PM source for slot2"
			::= { performance 17 }

		-- 1.3.6.1.4.1.43913.16.13.18
		teAlmLimitPPS1 OBJECT-TYPE
			SYNTAX Integer32 (0..1000000000)
			MAX-ACCESS read-write
			STATUS current
			DESCRIPTION
				"Time error alarm limit for PPS type signal of input1 module(in unit of ns)"
			::= { performance 18 }

		-- 1.3.6.1.4.1.43913.16.13.19
		teAlmLimitPPS2 OBJECT-TYPE
			SYNTAX Integer32 (0..1000000000)
			MAX-ACCESS read-write
			STATUS current
			DESCRIPTION
				"Time error alarm limit for PPS type signal of input2 module(in unit of ns)"
			::= { performance 19 }

		-- 1.3.6.1.4.1.43913.16.13.20
		teAlmLimitPTP1 OBJECT-TYPE
			SYNTAX Integer32 (0..50000000)
			MAX-ACCESS read-write
			STATUS current
			DESCRIPTION
				"Time error alarm limit for PTP-1 signal(in unit of ns)"
			::= { performance 20 }

		-- 1.3.6.1.4.1.43913.16.13.21
		teAlmLimitPTP2 OBJECT-TYPE
			SYNTAX Integer32 (0..50000000)
			MAX-ACCESS read-write
			STATUS current
			DESCRIPTION
				"Time error alarm limit for PTP-2 signal(in unit of ns)"
			::= { performance 21 }

		-- 1.3.6.1.4.1.43913.16.13.22
		teAutoCompState OBJECT-TYPE
			SYNTAX ActionState
			MAX-ACCESS read-write
			STATUS current
			DESCRIPTION
				"Show / Set time error auto compensation state, disable(0) or enable(1)"
			::= { performance 22 }

		-- 1.3.6.1.4.1.43913.16.13.23
		teCurrentPPS1 OBJECT-TYPE
			SYNTAX Integer32
			MAX-ACCESS read-only
			STATUS current
			DESCRIPTION
				"Show current time error of PPS-TOD-1(in unit of ns)"
			::= { performance 23 }

		-- 1.3.6.1.4.1.43913.16.13.24
		teCurrentPPS2 OBJECT-TYPE
			SYNTAX Integer32
			MAX-ACCESS read-only
			STATUS current
			DESCRIPTION
				"Show current time error of PPS-TOD-2(in unit of ns)"
			::= { performance 24 }

		-- 1.3.6.1.4.1.43913.16.13.25
		teCurrentPTP1 OBJECT-TYPE
			SYNTAX Integer32
			MAX-ACCESS read-only
			STATUS current
			DESCRIPTION
				"Show current time error of PTP-1(in unit of ns)"
			::= { performance 25 }

		-- 1.3.6.1.4.1.43913.16.13.26
		teCurrentPTP2 OBJECT-TYPE
			SYNTAX Integer32
			MAX-ACCESS read-only
			STATUS current
			DESCRIPTION
				"Show current time error of PTP-2(in unit of ns)"
			::= { performance 26 }

		-- 1.3.6.1.4.1.43913.16.13.27
		teDelayPPS1 OBJECT-TYPE
			SYNTAX Integer32 (-1000000..1000000)
			MAX-ACCESS read-write
			STATUS current
			DESCRIPTION
				"Time error manual delay for PPS-TOD-1(in unit of ns)"
			::= { performance 27 }

		-- 1.3.6.1.4.1.43913.16.13.28
		teDelayPPS2 OBJECT-TYPE
			SYNTAX Integer32 (-1000000..1000000)
			MAX-ACCESS read-write
			STATUS current
			DESCRIPTION
				"Time error manual delay for PPS-TOD-2(in unit of ns)"
			::= { performance 28 }

		-- 1.3.6.1.4.1.43913.16.13.29
		teDelayPTP1 OBJECT-TYPE
			SYNTAX Integer32 (-1000000..1000000)
			MAX-ACCESS read-write
			STATUS current
			DESCRIPTION
				"Time error manual delay for PTP-1(in unit of ns)"
			::= { performance 29 }

		-- 1.3.6.1.4.1.43913.16.13.30
		teDelayPTP2 OBJECT-TYPE
			SYNTAX Integer32 (-1000000..1000000)
			MAX-ACCESS read-write
			STATUS current
			DESCRIPTION
				"Time error manual delay for PTP-2(in unit of ns)"
			::= { performance 30 }

		-- 1.3.6.1.4.1.43913.16.13.31
		teAlmLimitNTP1 OBJECT-TYPE
			SYNTAX Integer32 (0..1000000000)
			MAX-ACCESS read-write
			STATUS current
			DESCRIPTION
				"Time error alarm limit for NTP-1 signal(in unit of ns)"
			::= { performance 31 }

		-- 1.3.6.1.4.1.43913.16.13.32
		teAlmLimitNTP2 OBJECT-TYPE
			SYNTAX Integer32 (0..1000000000)
			MAX-ACCESS read-write
			STATUS current
			DESCRIPTION
				"Time error alarm limit for NTP-2 signal(in unit of ns)"
			::= { performance 32 }

		-- 1.3.6.1.4.1.43913.16.16
		inpTTL OBJECT IDENTIFIER ::= { sm2000-5g 16 }


		-- 1.3.6.1.4.1.43913.16.16.1
		ttlTypePort1 OBJECT-TYPE
			SYNTAX TtlType
			MAX-ACCESS read-write
			STATUS current
			DESCRIPTION
				"The signal type of TTL channel. 0 - 10M, 1 - PPS"
			::= { inpTTL 1 }


		-- 1.3.6.1.4.1.43913.16.16.2
		ttlTypePort2 OBJECT-TYPE
			SYNTAX TtlType
			MAX-ACCESS read-write
			STATUS current
			DESCRIPTION
				"The signal type of TTL channel. 0 - 10M, 1 - PPS"
			::= { inpTTL 2 }


		-- 1.3.6.1.4.1.43913.16.16.3
		inputPPSTable OBJECT-TYPE
			SYNTAX SEQUENCE OF InputPPSEntry
			MAX-ACCESS not-accessible
			STATUS current
			DESCRIPTION
				"Input PPS configuration table."
			::= { inpTTL 3 }


		-- 1.3.6.1.4.1.43913.16.16.3.1
		inputPPSEntry OBJECT-TYPE
			SYNTAX InputPPSEntry
			MAX-ACCESS not-accessible
			STATUS current
			DESCRIPTION
				"The entry of input PPS configuration table."
			INDEX { inputPPSIndex }
			::= { inputPPSTable 1 }


		InputPPSEntry ::=
			SEQUENCE {
				inputPPSIndex
					Integer32,
				inputPPSPortID
					Integer32,
				inputPPSState
					ActionState,
				inputPPSPriority
					Integer32,
				inputPPSPQLState
					ActionState,
				inputPPSPQL
					Integer32
			 }

		-- 1.3.6.1.4.1.43913.16.16.3.1.1
		inputPPSIndex OBJECT-TYPE
			SYNTAX Integer32 (1..2)
			MAX-ACCESS not-accessible
			STATUS current
			DESCRIPTION
				"The index of input PPS configuration table."
			::= { inputPPSEntry 1 }


		-- 1.3.6.1.4.1.43913.16.16.3.1.2
		inputPPSPortID OBJECT-TYPE
			SYNTAX Integer32
			MAX-ACCESS read-only
			STATUS current
			DESCRIPTION
				"It should be port-1(1) or port-2(2)"
			::= { inputPPSEntry 2 }


		-- 1.3.6.1.4.1.43913.16.16.3.1.3
		inputPPSState OBJECT-TYPE
			SYNTAX ActionState
			MAX-ACCESS read-write
			STATUS current
			DESCRIPTION
				"Show / Set input PPS port state, disable(0) or enable(1)."
			::= { inputPPSEntry 3 }


		-- 1.3.6.1.4.1.43913.16.16.3.1.4
		inputPPSPriority OBJECT-TYPE
			SYNTAX Integer32 (0..20)
			MAX-ACCESS read-write
			STATUS current
			DESCRIPTION
				"Show / Set input PPS port priority."
			::= { inputPPSEntry 4 }


		-- 1.3.6.1.4.1.43913.16.16.3.1.5
		inputPPSPQLState OBJECT-TYPE
			SYNTAX ActionState
			MAX-ACCESS read-write
			STATUS current
			DESCRIPTION
				"Show / Set input PPS PQL state, disable(0) or enable(1)."
			::= { inputPPSEntry 5 }


		-- 1.3.6.1.4.1.43913.16.16.3.1.6
		inputPPSPQL OBJECT-TYPE
			SYNTAX Integer32
			MAX-ACCESS read-write
			STATUS current
			DESCRIPTION
				"Show / Set input PPS PQL value."
			::= { inputPPSEntry 6 }


		-- 1.3.6.1.4.1.43913.16.16.4
		input10MTable OBJECT-TYPE
			SYNTAX SEQUENCE OF Input10MEntry
			MAX-ACCESS not-accessible
			STATUS current
			DESCRIPTION
				"Input 10M configuration table."
			::= { inpTTL 4 }


		-- 1.3.6.1.4.1.43913.16.16.4.1
		input10MEntry OBJECT-TYPE
			SYNTAX Input10MEntry
			MAX-ACCESS not-accessible
			STATUS current
			DESCRIPTION
				"The entry of input 10M configuration table."
			INDEX { input10MIndex }
			::= { input10MTable 1 }


		Input10MEntry ::=
			SEQUENCE {
				input10MIndex
					Integer32,
				input10MPortID
					Integer32,
				input10MState
					ActionState,
				input10MPriority
					Integer32,
				input10MPQLState
					ActionState,
				input10MPQL
					Integer32
			 }

		-- 1.3.6.1.4.1.43913.16.16.4.1.1
		input10MIndex OBJECT-TYPE
			SYNTAX Integer32 (1..2)
			MAX-ACCESS not-accessible
			STATUS current
			DESCRIPTION
				"The index of input 10M configuration table."
			::= { input10MEntry 1 }


		-- 1.3.6.1.4.1.43913.16.16.4.1.2
		input10MPortID OBJECT-TYPE
			SYNTAX Integer32
			MAX-ACCESS read-only
			STATUS current
			DESCRIPTION
				"It should be port-1(1) or port-2(2)"
			::= { input10MEntry 2 }


		-- 1.3.6.1.4.1.43913.16.16.4.1.3
		input10MState OBJECT-TYPE
			SYNTAX ActionState
			MAX-ACCESS read-write
			STATUS current
			DESCRIPTION
				"Show / Set input 10M port state, disable(0) or enable(1)."
			::= { input10MEntry 3 }


		-- 1.3.6.1.4.1.43913.16.16.4.1.4
		input10MPriority OBJECT-TYPE
			SYNTAX Integer32 (0..20)
			MAX-ACCESS read-write
			STATUS current
			DESCRIPTION
				"Show / Set input 10M port priority."
			::= { input10MEntry 4 }


		-- 1.3.6.1.4.1.43913.16.16.4.1.5
		input10MPQLState OBJECT-TYPE
			SYNTAX ActionState
			MAX-ACCESS read-write
			STATUS current
			DESCRIPTION
				"Show / Set input 10M PQL state, disable(0) or enable(1)."
			::= { input10MEntry 5 }


		-- 1.3.6.1.4.1.43913.16.16.4.1.6
		input10MPQL OBJECT-TYPE
			SYNTAX Integer32
			MAX-ACCESS read-write
			STATUS current
			DESCRIPTION
				"Show / Set input 10M PQL value."
			::= { input10MEntry 6 }


		-- 1.3.6.1.4.1.43913.16.17
		delay OBJECT IDENTIFIER ::= { sm2000-5g 17 }


		-- 1.3.6.1.4.1.43913.16.17.7
		ppsTodDelayPort1 OBJECT-TYPE
			SYNTAX Integer32
			MAX-ACCESS read-write
			STATUS current
			DESCRIPTION
				"The delay of input PPS port 1. in unit of ns"
			::= { delay 7 }


		-- 1.3.6.1.4.1.43913.16.17.8
		ppsTodDelayPort2 OBJECT-TYPE
			SYNTAX Integer32
			MAX-ACCESS read-write
			STATUS current
			DESCRIPTION
				"The delay of input PPS port 2. in unit of ns"
			::= { delay 8 }


		-- 1.3.6.1.4.1.43913.16.17.9
		ppsDelayPort1 OBJECT-TYPE
			SYNTAX Integer32
			MAX-ACCESS read-write
			STATUS current
			DESCRIPTION
				"The delay of input PPS port 1. in unit of ns"
			::= { delay 9 }


		-- 1.3.6.1.4.1.43913.16.17.10
		ppsDelayPort2 OBJECT-TYPE
			SYNTAX Integer32
			MAX-ACCESS read-write
			STATUS current
			DESCRIPTION
				"The delay of input PPS port 2. in unit of ns"
			::= { delay 10 }


		-- 1.3.6.1.4.1.43913.16.17.11
		irigDelayPort1 OBJECT-TYPE
			SYNTAX Integer32
			MAX-ACCESS read-write
			STATUS current
			DESCRIPTION
				"The delay of input IRIG port 1. in unit of ns"
			::= { delay 11 }


		-- 1.3.6.1.4.1.43913.16.17.12
		irigDelayPort2 OBJECT-TYPE
			SYNTAX Integer32
			MAX-ACCESS read-write
			STATUS current
			DESCRIPTION
				"The delay of input IRIG port 2. in unit of ns"
			::= { delay 12 }


		-- 1.3.6.1.4.1.43913.16.17.13
		gnssDelayPort1 OBJECT-TYPE
			SYNTAX Integer32
			MAX-ACCESS read-write
			STATUS current
			DESCRIPTION
				"The delay of input GNSS port 1. in unit of ns"
			::= { delay 13 }


		-- 1.3.6.1.4.1.43913.16.17.14
		gnssDelayPort2 OBJECT-TYPE
			SYNTAX Integer32
			MAX-ACCESS read-write
			STATUS current
			DESCRIPTION
				"The delay of input GNSS port 2. in unit of ns"
			::= { delay 14 }


		-- 1.3.6.1.4.1.43913.16.18
		ptp OBJECT IDENTIFIER ::= { sm2000-5g 18 }


		-- 1.3.6.1.4.1.43913.16.18.1
		ptpTable OBJECT-TYPE
			SYNTAX SEQUENCE OF PtpEntry
			MAX-ACCESS not-accessible
			STATUS current
			DESCRIPTION
				"PTP input configuration table."
			::= { ptp 1 }


		-- 1.3.6.1.4.1.43913.16.18.1.1
		ptpEntry OBJECT-TYPE
			SYNTAX PtpEntry
			MAX-ACCESS not-accessible
			STATUS current
			DESCRIPTION
				"The entry of PTP input configuration table."
			INDEX { ptpIndex }
			::= { ptpTable 1 }


		PtpEntry ::=
			SEQUENCE {
				ptpIndex
					Integer32,
				ptpPortID
					Integer32,
				ptpState
					ActionState,
				ptpProfile
					InputPTPprofile,
				ptpGM1State
					ActionState,
				ptpGM1Address
					DisplayString,
				ptpGM2State
					ActionState,
				ptpGM2Address
					DisplayString,
				ptpAnnIntv
					Integer32,
				ptpSyncIntv
					Integer32,
				ptpDelayIntv
					Integer32,
				ptpDomain
					Unsigned32,
				ptpLocalPrio
					Unsigned32,
				ptpMasterOnly
					MasterOnlyEnable,
				ptpPriority2
					Unsigned32,
				ptpTxDelay
					Unsigned32,
				ptpRxDelay
					Unsigned32,
				ptpRefPrio
					Unsigned32,
				ptpPQLState
					ActionState,
				ptpQLCfgValue
					ClkQL,
				ptpPeerMode
					ActionState
			 }

		-- 1.3.6.1.4.1.43913.16.18.1.1.1
		ptpIndex OBJECT-TYPE
			SYNTAX Integer32 (1..2)
			MAX-ACCESS not-accessible
			STATUS current
			DESCRIPTION
				"The index of PTP configuration table."
			::= { ptpEntry 1 }


		-- 1.3.6.1.4.1.43913.16.18.1.1.2
		ptpPortID OBJECT-TYPE
			SYNTAX Integer32
			MAX-ACCESS read-only
			STATUS current
			DESCRIPTION
				"It should be port-1(1) or port-2(2)"
			::= { ptpEntry 2 }


		-- 1.3.6.1.4.1.43913.16.18.1.1.3
		ptpState OBJECT-TYPE
			SYNTAX ActionState
			MAX-ACCESS read-write
			STATUS current
			DESCRIPTION
				"Show / Set PTP port state, disable(0) or enable(1)."
			::= { ptpEntry 3 }


		-- 1.3.6.1.4.1.43913.16.18.1.1.4
		ptpProfile OBJECT-TYPE
			SYNTAX InputPTPprofile
			MAX-ACCESS read-write
			STATUS current
			DESCRIPTION
				"Show / Set ptp profile."
			::= { ptpEntry 4 }


		-- 1.3.6.1.4.1.43913.16.18.1.1.5
		ptpGM1State OBJECT-TYPE
			SYNTAX ActionState
			MAX-ACCESS read-write
			STATUS current
			DESCRIPTION
				"Show / Set PTP GM1 state, disable(0) or enable(1)"
			::= { ptpEntry 5 }


		-- 1.3.6.1.4.1.43913.16.18.1.1.6
		ptpGM1Address OBJECT-TYPE
			SYNTAX DisplayString
			MAX-ACCESS read-write
			STATUS current
			DESCRIPTION
				"Show / Set PTP GM1 address"
			::= { ptpEntry 6 }


		-- 1.3.6.1.4.1.43913.16.18.1.1.7
		ptpGM2State OBJECT-TYPE
			SYNTAX ActionState
			MAX-ACCESS read-write
			STATUS current
			DESCRIPTION
				"Show / Set PTP GM2 state, disable(0) or enable(1)"
			::= { ptpEntry 7 }


		-- 1.3.6.1.4.1.43913.16.18.1.1.8
		ptpGM2Address OBJECT-TYPE
			SYNTAX DisplayString
			MAX-ACCESS read-write
			STATUS current
			DESCRIPTION
				"Show / Set PTP GM2 address"
			::= { ptpEntry 8 }


		-- 1.3.6.1.4.1.43913.16.18.1.1.9
		ptpAnnIntv OBJECT-TYPE
			SYNTAX Integer32
			MAX-ACCESS read-write
			STATUS current
			DESCRIPTION
				"Show / Set PTP announce interval."
			::= { ptpEntry 9 }


		-- 1.3.6.1.4.1.43913.16.18.1.1.10
		ptpSyncIntv OBJECT-TYPE
			SYNTAX Integer32
			MAX-ACCESS read-write
			STATUS current
			DESCRIPTION
				"Show / Set PTP sync interval."
			::= { ptpEntry 10 }


		-- 1.3.6.1.4.1.43913.16.18.1.1.11
		ptpDelayIntv OBJECT-TYPE
			SYNTAX Integer32
			MAX-ACCESS read-write
			STATUS current
			DESCRIPTION
				"Show / Set PTP delay interval."
			::= { ptpEntry 11 }


		-- 1.3.6.1.4.1.43913.16.18.1.1.12
		ptpDomain OBJECT-TYPE
			SYNTAX Unsigned32
			MAX-ACCESS read-write
			STATUS current
			DESCRIPTION
				"Show / Set PTP domain value."
			::= { ptpEntry 12 }


		-- 1.3.6.1.4.1.43913.16.18.1.1.13
		ptpLocalPrio OBJECT-TYPE
			SYNTAX Unsigned32
			MAX-ACCESS read-write
			STATUS current
			DESCRIPTION
				"Show / Set PTP local priority value."
			::= { ptpEntry 13 }


		-- 1.3.6.1.4.1.43913.16.18.1.1.14
		ptpMasterOnly OBJECT-TYPE
			SYNTAX MasterOnlyEnable
			MAX-ACCESS read-write
			STATUS current
			DESCRIPTION
				"Show / Set PTP master only, no(0) or yes(1)."
			::= { ptpEntry 14 }


		-- 1.3.6.1.4.1.43913.16.18.1.1.15
		ptpPriority2 OBJECT-TYPE
			SYNTAX Unsigned32
			MAX-ACCESS read-write
			STATUS current
			DESCRIPTION
				"Show / Set PTP priority 2."
			::= { ptpEntry 15 }


		-- 1.3.6.1.4.1.43913.16.18.1.1.16
		ptpTxDelay OBJECT-TYPE
			SYNTAX Unsigned32
			MAX-ACCESS read-write
			STATUS current
			DESCRIPTION
				"Show / Set PTP tx timestamp delay value."
			::= { ptpEntry 16 }


		-- 1.3.6.1.4.1.43913.16.18.1.1.17
		ptpRxDelay OBJECT-TYPE
			SYNTAX Unsigned32
			MAX-ACCESS read-write
			STATUS current
			DESCRIPTION
				"Show / Set PTP rx timestamp delay value."
			::= { ptpEntry 17 }


		-- 1.3.6.1.4.1.43913.16.18.1.1.18
		ptpRefPrio OBJECT-TYPE
			SYNTAX Unsigned32 (0..20)
			MAX-ACCESS read-write
			STATUS current
			DESCRIPTION
				"Show / Set PTP reference priority."
			::= { ptpEntry 18 }


		-- 1.3.6.1.4.1.43913.16.18.1.1.19
		ptpPQLState OBJECT-TYPE
			SYNTAX ActionState
			MAX-ACCESS read-write
			STATUS current
			DESCRIPTION
				"Show / Set PTP PQL state, disable(0) or enable(1)."
			::= { ptpEntry 19 }


		-- 1.3.6.1.4.1.43913.16.18.1.1.20
		ptpQLCfgValue OBJECT-TYPE
			SYNTAX ClkQL
			MAX-ACCESS read-write
			STATUS current
			DESCRIPTION
				"Show / Set PTP QL value."
			::= { ptpEntry 20 }


		-- 1.3.6.1.4.1.43913.16.18.1.1.21
		ptpPeerMode OBJECT-TYPE
			SYNTAX ActionState
			MAX-ACCESS read-write
			STATUS current
			DESCRIPTION
				"Show / Set PTP peer mode state, disable(0) or enable(1)."
			::= { ptpEntry 21 }


		-- 1.3.6.1.4.1.43913.16.18.2
		ptpStatusTable OBJECT-TYPE
			SYNTAX SEQUENCE OF PtpStatusEntry
			MAX-ACCESS not-accessible
			STATUS current
			DESCRIPTION
				"PTP input status table."
			::= { ptp 2 }


		-- 1.3.6.1.4.1.43913.16.18.2.1
		ptpStatusEntry OBJECT-TYPE
			SYNTAX PtpStatusEntry
			MAX-ACCESS not-accessible
			STATUS current
			DESCRIPTION
				"The entry of PTP input status table."
			INDEX { ptpStatusIndex }
			::= { ptpStatusTable 1 }


		PtpStatusEntry ::=
			SEQUENCE {
				ptpStatusIndex
					Integer32,
				ptpStatusPortID
					Integer32,
				ptpStatusGMClockID
					DisplayString,
				ptpStatusSyncRate
					Integer32,
				ptpStatusDelayRate
					Integer32,
				ptpStatusT2T1Offset
					Integer32,
				ptpStatusOffset
					Integer32
			 }

		-- 1.3.6.1.4.1.43913.16.18.2.1.1
		ptpStatusIndex OBJECT-TYPE
			SYNTAX Integer32 (1..2)
			MAX-ACCESS not-accessible
			STATUS current
			DESCRIPTION
				"The index of PTP status table."
			::= { ptpStatusEntry 1 }


		-- 1.3.6.1.4.1.43913.16.18.2.1.2
		ptpStatusPortID OBJECT-TYPE
			SYNTAX Integer32
			MAX-ACCESS read-only
			STATUS current
			DESCRIPTION
				"It should be port-1(1) or port-2(2)"
			::= { ptpStatusEntry 2 }


		-- 1.3.6.1.4.1.43913.16.18.2.1.3
		ptpStatusGMClockID OBJECT-TYPE
			SYNTAX DisplayString
			MAX-ACCESS read-only
			STATUS current
			DESCRIPTION
				"Show PTP GM clock ID."
			::= { ptpStatusEntry 3 }


		-- 1.3.6.1.4.1.43913.16.18.2.1.4
		ptpStatusSyncRate OBJECT-TYPE
			SYNTAX Integer32
			MAX-ACCESS read-only
			STATUS current
			DESCRIPTION
				"Show PTP syn packet rate (pkts/s)."
			::= { ptpStatusEntry 4 }


		-- 1.3.6.1.4.1.43913.16.18.2.1.5
		ptpStatusDelayRate OBJECT-TYPE
			SYNTAX Integer32
			MAX-ACCESS read-only
			STATUS current
			DESCRIPTION
				"Show PTP delay packet rate (pkts/s)."
			::= { ptpStatusEntry 5 }


		-- 1.3.6.1.4.1.43913.16.18.2.1.6
		ptpStatusT2T1Offset OBJECT-TYPE
			SYNTAX Integer32
			MAX-ACCESS read-only
			STATUS current
			DESCRIPTION
				"Show PTP T2-T1 offset (ns)."
			::= { ptpStatusEntry 6 }


		-- 1.3.6.1.4.1.43913.16.18.2.1.7
		ptpStatusOffset OBJECT-TYPE
			SYNTAX Integer32
			MAX-ACCESS read-only
			STATUS current
			DESCRIPTION
				"Show PTP offset (ns)."
			::= { ptpStatusEntry 7 }


		-- 1.3.6.1.4.1.43913.16.18.3
		ptpRxAnnMsgTable OBJECT-TYPE
			SYNTAX SEQUENCE OF PtpRxAnnMsgEntry
			MAX-ACCESS not-accessible
			STATUS current
			DESCRIPTION
				"This table is used to get PTP rx announce message of input PTP ports."
			::= { ptp 3 }


		-- 1.3.6.1.4.1.43913.16.18.3.1
		ptpRxAnnMsgEntry OBJECT-TYPE
			SYNTAX PtpRxAnnMsgEntry
			MAX-ACCESS not-accessible
			STATUS current
			DESCRIPTION
				"The entry of the table."
			INDEX { ptpRxAnnMsgPortIndex, ptpRxAnnMsgIndex }
			::= { ptpRxAnnMsgTable 1 }


		PtpRxAnnMsgEntry ::=
			SEQUENCE {
				ptpRxAnnMsgPortIndex
					Integer32,
				ptpRxAnnMsgIndex
					Integer32,
				ptpRxAnnMsgClockID
					DisplayString,
				ptpRxAnnMsgClockClass
					Integer32,
				ptpRxAnnMsgClockAccuracy
					Integer32,
				ptpRxAnnMsgClockVariance
					Integer32,
				ptpRxAnnMsgPriority1
					Integer32,
				ptpRxAnnMsgPriority2
					Integer32,
				ptpRxAnnMsgTimeSource
					DisplayString,
				ptpRxAnnMsgUtcOffset
					Integer32
			 }


		-- 1.3.6.1.4.1.43913.16.8.18.3.1.1
		ptpRxAnnMsgPortIndex  OBJECT-TYPE
			SYNTAX Integer32 (1..2)
			MAX-ACCESS read-only
			STATUS current
			DESCRIPTION
				"The port index."
			::= { ptpRxAnnMsgEntry 1 }


		-- 1.3.6.1.4.1.43913.16.8.18.3.1.2
		ptpRxAnnMsgIndex OBJECT-TYPE
			SYNTAX Integer32
			MAX-ACCESS read-only
			STATUS current
			DESCRIPTION
				"The port index."
			::= { ptpRxAnnMsgEntry 2 }


		-- 1.3.6.1.4.1.43913.16.8.18.3.1.3
		ptpRxAnnMsgClockID  OBJECT-TYPE
			SYNTAX DisplayString
			MAX-ACCESS read-only
			STATUS current
			DESCRIPTION
				"The clock id."
			::= { ptpRxAnnMsgEntry 3 }


		-- 1.3.6.1.4.1.43913.16.8.18.3.1.4
		ptpRxAnnMsgClockClass  OBJECT-TYPE
			SYNTAX Integer32
			MAX-ACCESS read-only
			STATUS current
			DESCRIPTION
				"The clock class."
			::= { ptpRxAnnMsgEntry 4 }


		-- 1.3.6.1.4.1.43913.16.8.18.3.1.5
		ptpRxAnnMsgClockAccuracy  OBJECT-TYPE
			SYNTAX Integer32
			MAX-ACCESS read-only
			STATUS current
			DESCRIPTION
				"The clock accuracy."
			::= { ptpRxAnnMsgEntry 5 }


		-- 1.3.6.1.4.1.43913.16.8.18.3.1.6
		ptpRxAnnMsgClockVariance  OBJECT-TYPE
			SYNTAX Integer32
			MAX-ACCESS read-only
			STATUS current
			DESCRIPTION
				"The clock variance."
			::= { ptpRxAnnMsgEntry 6 }


		-- 1.3.6.1.4.1.43913.16.8.18.3.1.7
		ptpRxAnnMsgPriority1  OBJECT-TYPE
			SYNTAX Integer32
			MAX-ACCESS read-only
			STATUS current
			DESCRIPTION
				"The priority 1."
			::= { ptpRxAnnMsgEntry 7 }


		-- 1.3.6.1.4.1.43913.16.8.18.3.1.8
		ptpRxAnnMsgPriority2  OBJECT-TYPE
			SYNTAX Integer32
			MAX-ACCESS read-only
			STATUS current
			DESCRIPTION
				"The priority 2."
			::= { ptpRxAnnMsgEntry 8 }


		-- 1.3.6.1.4.1.43913.16.8.18.3.1.9
		ptpRxAnnMsgTimeSource  OBJECT-TYPE
			SYNTAX DisplayString
			MAX-ACCESS read-only
			STATUS current
			DESCRIPTION
				"The time source."
			::= { ptpRxAnnMsgEntry 9 }


		-- 1.3.6.1.4.1.43913.16.8.18.3.1.10
		ptpRxAnnMsgUtcOffset  OBJECT-TYPE
			SYNTAX Integer32
			MAX-ACCESS read-only
			STATUS current
			DESCRIPTION
				"The UTC offset."
			::= { ptpRxAnnMsgEntry 10 }


		-- 1.3.6.1.4.1.43913.16.19
		synce OBJECT IDENTIFIER ::= { sm2000-5g 19 }


		-- 1.3.6.1.4.1.43913.16.19.1
		ethSrcTypePort1 OBJECT-TYPE
			SYNTAX EthSrcType
			MAX-ACCESS read-write
			STATUS current
			DESCRIPTION
				"The source type of ETH1. 0 - PTP, 1 - SyncE, 2 - PTP-SyncE"
			::= { synce 1 }


		-- 1.3.6.1.4.1.43913.16.19.2
		ethSrcTypePort2 OBJECT-TYPE
			SYNTAX EthSrcType
			MAX-ACCESS read-write
			STATUS current
			DESCRIPTION
				"The source type of ETH1. 0 - PTP, 1 - SyncE, 2 - PTP-SyncE"
			::= { synce 2 }


		-- 1.3.6.1.4.1.43913.16.19.3
		synceStatePort1 OBJECT-TYPE
			SYNTAX ActionState
			MAX-ACCESS read-write
			STATUS current
			DESCRIPTION
				"The SyncE state of port1."
			::= { synce 3 }


		-- 1.3.6.1.4.1.43913.16.19.4
		syncePrioPort1 OBJECT-TYPE
			SYNTAX Integer32
			MAX-ACCESS read-write
			STATUS current
			DESCRIPTION
				"The SyncE priority of port1."
			::= { synce 4 }


		-- 1.3.6.1.4.1.43913.16.19.5
		syncePQLStatePort1 OBJECT-TYPE
			SYNTAX ActionState
			MAX-ACCESS read-write
			STATUS current
			DESCRIPTION
				"The SyncE PQL state of port1."
			::= { synce 5 }


		-- 1.3.6.1.4.1.43913.16.19.6
		syncePQLPort1 OBJECT-TYPE
			SYNTAX ClkQL
			MAX-ACCESS read-write
			STATUS current
			DESCRIPTION
				"The SyncE PQL value of port1."
			::= { synce 6 }


		-- 1.3.6.1.4.1.43913.16.19.7
		synceStatePort2 OBJECT-TYPE
			SYNTAX ActionState
			MAX-ACCESS read-write
			STATUS current
			DESCRIPTION
				"The SyncE state of port2."
			::= { synce 7 }


		-- 1.3.6.1.4.1.43913.16.19.8
		syncePrioPort2 OBJECT-TYPE
			SYNTAX Integer32
			MAX-ACCESS read-write
			STATUS current
			DESCRIPTION
				"The SyncE priority of port2."
			::= { synce 8 }


		-- 1.3.6.1.4.1.43913.16.19.9
		syncePQLStatePort2 OBJECT-TYPE
			SYNTAX ActionState
			MAX-ACCESS read-write
			STATUS current
			DESCRIPTION
				"The SyncE PQL state of port2."
			::= { synce 9 }


		-- 1.3.6.1.4.1.43913.16.19.10
		syncePQLPort2 OBJECT-TYPE
			SYNTAX ClkQL
			MAX-ACCESS read-write
			STATUS current
			DESCRIPTION
				"The SyncE PQL value of port2."
			::= { synce 10 }

		-- 1.3.6.1.4.1.43913.16.20
		ntpInput OBJECT IDENTIFIER ::= { sm2000-5g 20 }


		-- 1.3.6.1.4.1.43913.16.20.1
		ntpInputTable OBJECT-TYPE
			SYNTAX SEQUENCE OF NtpInputEntry
			MAX-ACCESS not-accessible
			STATUS current
			DESCRIPTION
				"NTP input configuration table."
			::= { ntpInput 1 }


		-- 1.3.6.1.4.1.43913.16.20.1.1
		ntpInputEntry OBJECT-TYPE
			SYNTAX NtpInputEntry
			MAX-ACCESS not-accessible
			STATUS current
			DESCRIPTION
				"The entry of NTP input configuration table."
			INDEX { ntpInputIndex }
			::= { ntpInputTable 1 }


		NtpInputEntry ::=
			SEQUENCE {
				ntpInputIndex
					Integer32,
				ntpInputPortID
					Integer32,
				ntpInputState
					ActionState,
				ntpInputPriority
					Integer32,
				ntpInputPQLState
					ActionState,
				ntpInputPQL
					Integer32,
				ntpInputServerIP
					DisplayString,
				ntpInputDelay
					Integer32,
				ntpInputSyncLimit
					Integer32
			 }

		-- 1.3.6.1.4.1.43913.16.20.1.1.1
		ntpInputIndex OBJECT-TYPE
			SYNTAX Integer32 (1..2)
			MAX-ACCESS not-accessible
			STATUS current
			DESCRIPTION
				"The index of NTP input configuration table."
			::= { ntpInputEntry 1 }


		-- 1.3.6.1.4.1.43913.16.20.1.1.2
		ntpInputPortID OBJECT-TYPE
			SYNTAX Integer32
			MAX-ACCESS read-only
			STATUS current
			DESCRIPTION
				"It should be port-1(1) or port-2(2)"
			::= { ntpInputEntry 2 }


		-- 1.3.6.1.4.1.43913.16.20.1.1.3
		ntpInputState OBJECT-TYPE
			SYNTAX ActionState
			MAX-ACCESS read-write
			STATUS current
			DESCRIPTION
				"Show / Set NTP input port state, disable(0) or enable(1)."
			::= { ntpInputEntry 3 }


		-- 1.3.6.1.4.1.43913.16.20.1.1.4
		ntpInputPriority OBJECT-TYPE
			SYNTAX Integer32 (0..20)
			MAX-ACCESS read-write
			STATUS current
			DESCRIPTION
				"Show / Set NTP input port priority."
			::= { ntpInputEntry 4 }


		-- 1.3.6.1.4.1.43913.16.20.1.1.5
		ntpInputPQLState OBJECT-TYPE
			SYNTAX ActionState
			MAX-ACCESS read-write
			STATUS current
			DESCRIPTION
				"Show / Set NTP input PQL state, disable(0) or enable(1)."
			::= { ntpInputEntry 5 }


		-- 1.3.6.1.4.1.43913.16.20.1.1.6
		ntpInputPQL OBJECT-TYPE
			SYNTAX Integer32
			MAX-ACCESS read-write
			STATUS current
			DESCRIPTION
				"Show / Set NTP input PQL value."
			::= { ntpInputEntry 6 }

		-- 1.3.6.1.4.1.43913.16.20.1.1.7
		ntpInputServerIP OBJECT-TYPE
			SYNTAX DisplayString
			MAX-ACCESS read-write
			STATUS current
			DESCRIPTION
				"NTP input server IP."
			::= { ntpInputEntry 7 }


		-- 1.3.6.1.4.1.43913.16.20.1.1.8
		ntpInputDelay OBJECT-TYPE
			SYNTAX Integer32
			MAX-ACCESS read-write
			STATUS current
			DESCRIPTION
				"-100000000ns~100000000ns"
			::= { ntpInputEntry 8 }

		-- 1.3.6.1.4.1.43913.16.20.1.1.9
		ntpInputSyncLimit OBJECT-TYPE
			SYNTAX Integer32
			MAX-ACCESS read-write
			STATUS current
			DESCRIPTION
				"100ns~100000000ns"
			::= { ntpInputEntry 9 }


	END

--
-- SM2000-5G-MIB.txt
--
